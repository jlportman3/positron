-- *****************************************************************
-- IP-MIB:  Positron's GAM private MIB
-- *****************************************************************

GAM-IP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    GAMDisplayString FROM GAM-TC
    GAMInterfaceIndex FROM GAM-TC
    GAMRowEditorState FROM GAM-TC
    GAMUnsigned8 FROM GAM-TC
    InetAddressIPv6 FROM INET-ADDRESS-MIB
    Counter64 FROM SNMPv2-SMI
    Integer32 FROM SNMPv2-SMI
    IpAddress FROM SNMPv2-SMI
    Unsigned32 FROM SNMPv2-SMI
    MacAddress FROM SNMPv2-TC
    TruthValue FROM SNMPv2-TC
    ;

gamIpMib MODULE-IDENTITY
    LAST-UPDATED "201705240000Z"
    ORGANIZATION
        "Positron Access Solutions Corp."
    CONTACT-INFO
        "Customer Service <info@positronaccess.com>"
    DESCRIPTION
        "Private IP MIB."
    REVISION    "201705240000Z"
    DESCRIPTION
        "Add DHCP client hostname and client identifier configuration."
    REVISION    "201607280000Z"
    DESCRIPTION
        "Add ability to clear address conflict detection table."
    REVISION    "201508240000Z"
    DESCRIPTION
        "Add capability for IPv4/IPv6 statistics availability."
    REVISION    "201410290000Z"
    DESCRIPTION
        "Removed the fields arpRetransmitTime and reasmMaxSize."
    REVISION    "201410210000Z"
    DESCRIPTION
        "Added arpCheck in the DhcpClientState enum"
    REVISION    "201409110000Z"
    DESCRIPTION
        "Revise definition of IPv4/IPv6 interface status table index."
    REVISION    "201407010000Z"
    DESCRIPTION
        "Initial version."
    ::= { gamMgmt 102 }


GAMIpDhcpClientState ::= TEXTUAL-CONVENTION
    STATUS      current
    DESCRIPTION
        "-"
    SYNTAX      INTEGER { stopped(0), init(1), selecting(2),
                          requesting(3), rebinding(4), bound(5),
                          renewing(6), fallback(7), arpCheck(8) }

GAMIpDhcpClientType ::= TEXTUAL-CONVENTION
    STATUS      current
    DESCRIPTION
        "The type of the DHCP client identifier."
    SYNTAX      INTEGER { auto(0), ifmac(1), ascii(2), hex(3) }

gamIpMibObjects OBJECT IDENTIFIER
    ::= { gamIpMib 1 }

gamIpCapabilities OBJECT IDENTIFIER
    ::= { gamIpMibObjects 1 }

gamIpCapabilitiesHasIpv4HostCapabilities OBJECT-TYPE
    SYNTAX      TruthValue
    MAX-ACCESS  read-only
    STATUS      current
    DESCRIPTION
        "The device has IPv4 host capabilities for management."
    ::= { gamIpCapabilities 1 }

gamIpCapabilitiesHasIpv6HostCapabilities OBJECT-TYPE
    SYNTAX      TruthValue
    MAX-ACCESS  read-only
    STATUS      current
    DESCRIPTION
        "The device has IPv6 host capabilities for management."
    ::= { gamIpCapabilities 2 }

gamIpCapabilitiesHasIpv4UnicastRoutingCapabilities OBJECT-TYPE
    SYNTAX      TruthValue
    MAX-ACCESS  read-only
    STATUS      current
    DESCRIPTION
        "The device has IPv4 unicast routing capabilities."
    ::= { gamIpCapabilities 3 }

gamIpCapabilitiesHasIpv4UnicastHwRoutingCapabilities OBJECT-TYPE
    SYNTAX      TruthValue
    MAX-ACCESS  read-only
    STATUS      current
    DESCRIPTION
        "The device has IPv4 unicast hardware accelerated routing capabilities."
    ::= { gamIpCapabilities 4 }

gamIpCapabilitiesHasIpv6UnicastRoutingCapabilities OBJECT-TYPE
    SYNTAX      TruthValue
    MAX-ACCESS  read-only
    STATUS      current
    DESCRIPTION
        "The device has IPv6 unicast routing capabilities."
    ::= { gamIpCapabilities 5 }

gamIpCapabilitiesHasIpv6UnicastHwRoutingCapabilities OBJECT-TYPE
    SYNTAX      TruthValue
    MAX-ACCESS  read-only
    STATUS      current
    DESCRIPTION
        "The device has IPv6 unicast hardware accelerated routing capabilities."
    ::= { gamIpCapabilities 6 }

gamIpCapabilitiesMaxNumberOfIpInterfaces OBJECT-TYPE
    SYNTAX      Unsigned32
    MAX-ACCESS  read-only
    STATUS      current
    DESCRIPTION
        "Maximum number of IP interfaces supported by the device."
    ::= { gamIpCapabilities 7 }

gamIpCapabilitiesMaxNumberOfStaticRoutes OBJECT-TYPE
    SYNTAX      Unsigned32
    MAX-ACCESS  read-only
    STATUS      current
    DESCRIPTION
        "Maximum number of static configured IP routes (shared by IPv4 and
         IPv6)."
    ::= { gamIpCapabilities 8 }

gamIpCapabilitiesNumberOfLpmHardwareEntries OBJECT-TYPE
    SYNTAX      Unsigned32
    MAX-ACCESS  read-only
    STATUS      current
    DESCRIPTION
        "Number of hardware LPM (longest prefix match) entries."
    ::= { gamIpCapabilities 9 }

gamIpCapabilitiesHasPerInterfaceIpv4Statistics OBJECT-TYPE
    SYNTAX      TruthValue
    MAX-ACCESS  read-only
    STATUS      current
    DESCRIPTION
        "If true, the platform supports detailed IPv4 statistics per interface."
    ::= { gamIpCapabilities 10 }

gamIpCapabilitiesHasPerInterfaceIpv6Statistics OBJECT-TYPE
    SYNTAX      TruthValue
    MAX-ACCESS  read-only
    STATUS      current
    DESCRIPTION
        "If true, the platform supports detailed IPv6 statistics per interface."
    ::= { gamIpCapabilities 11 }

gamIpConfig OBJECT IDENTIFIER
    ::= { gamIpMibObjects 2 }

gamIpConfigGlobals OBJECT IDENTIFIER
    ::= { gamIpConfig 1 }

gamIpConfigGlobalsMain OBJECT IDENTIFIER
    ::= { gamIpConfigGlobals 1 }

gamIpConfigGlobalsMainEnableRouting OBJECT-TYPE
    SYNTAX      TruthValue
    MAX-ACCESS  read-write
    STATUS      current
    DESCRIPTION
        "Enable routing."
    ::= { gamIpConfigGlobalsMain 1 }

gamIpConfigInterfaces OBJECT IDENTIFIER
    ::= { gamIpConfig 2 }

gamIpConfigInterfacesTable OBJECT-TYPE
    SYNTAX      SEQUENCE OF GAMIpConfigInterfacesEntry
    MAX-ACCESS  not-accessible
    STATUS      current
    DESCRIPTION
        "This is the IP interface table. When an IP interface is created it can
         be configured in the other tables found in this MIB."
    ::= { gamIpConfigInterfaces 1 }

gamIpConfigInterfacesEntry OBJECT-TYPE
    SYNTAX      GAMIpConfigInterfacesEntry
    MAX-ACCESS  not-accessible
    STATUS      current
    DESCRIPTION
        "Entries in this table represent IP interfaces created on the system"
    INDEX       { gamIpConfigInterfacesIfIndex }
    ::= { gamIpConfigInterfacesTable 1 }

GAMIpConfigInterfacesEntry ::= SEQUENCE {
    gamIpConfigInterfacesIfIndex  GAMInterfaceIndex,
    gamIpConfigInterfacesAction   GAMRowEditorState
}

gamIpConfigInterfacesIfIndex OBJECT-TYPE
    SYNTAX      GAMInterfaceIndex
    MAX-ACCESS  accessible-for-notify
    STATUS      current
    DESCRIPTION
        "Interface index number."
    ::= { gamIpConfigInterfacesEntry 1 }

gamIpConfigInterfacesAction OBJECT-TYPE
    SYNTAX      GAMRowEditorState
    MAX-ACCESS  read-write
    STATUS      current
    DESCRIPTION
        "Action"
    ::= { gamIpConfigInterfacesEntry 100 }

gamIpConfigInterfacesTableRowEditor OBJECT IDENTIFIER
    ::= { gamIpConfigInterfaces 2 }

gamIpConfigInterfacesTableRowEditorIfIndex OBJECT-TYPE
    SYNTAX      GAMInterfaceIndex
    MAX-ACCESS  read-write
    STATUS      current
    DESCRIPTION
        "Interface index number."
    ::= { gamIpConfigInterfacesTableRowEditor 1 }

gamIpConfigInterfacesTableRowEditorAction OBJECT-TYPE
    SYNTAX      GAMRowEditorState
    MAX-ACCESS  read-write
    STATUS      current
    DESCRIPTION
        "Action"
    ::= { gamIpConfigInterfacesTableRowEditor 100 }

gamIpConfigInterfacesIpv4Table OBJECT-TYPE
    SYNTAX      SEQUENCE OF GAMIpConfigInterfacesIpv4Entry
    MAX-ACCESS  not-accessible
    STATUS      current
    DESCRIPTION
        "IPv4 interface configuration table. This table enables IPv4 related
         configuration of the corresponding IP interface."
    ::= { gamIpConfigInterfaces 3 }

gamIpConfigInterfacesIpv4Entry OBJECT-TYPE
    SYNTAX      GAMIpConfigInterfacesIpv4Entry
    MAX-ACCESS  not-accessible
    STATUS      current
    DESCRIPTION
        "Each entry in this table represents an IP interface."
    INDEX       { gamIpConfigInterfacesIpv4IfIndex }
    ::= { gamIpConfigInterfacesIpv4Table 1 }

GAMIpConfigInterfacesIpv4Entry ::= SEQUENCE {
    gamIpConfigInterfacesIpv4IfIndex                    GAMInterfaceIndex,
    gamIpConfigInterfacesIpv4Active                     TruthValue,
    gamIpConfigInterfacesIpv4EnableDhcpClient           TruthValue,
    gamIpConfigInterfacesIpv4Ipv4Address                IpAddress,
    gamIpConfigInterfacesIpv4PrefixSize                 Unsigned32,
    gamIpConfigInterfacesIpv4DhcpClientFallbackTimeout  Unsigned32,
    gamIpConfigInterfacesIpv4DhcpClientHostname         GAMDisplayString,
    gamIpConfigInterfacesIpv4DhcpClientIdType           GAMIpDhcpClientType,
    gamIpConfigInterfacesIpv4DhcpClientIdIfMac          GAMInterfaceIndex,
    gamIpConfigInterfacesIpv4DhcpClientIdAscii          GAMDisplayString,
    gamIpConfigInterfacesIpv4DhcpClientIdHex            GAMDisplayString
}

gamIpConfigInterfacesIpv4IfIndex OBJECT-TYPE
    SYNTAX      GAMInterfaceIndex
    MAX-ACCESS  accessible-for-notify
    STATUS      current
    DESCRIPTION
        "Interface index number."
    ::= { gamIpConfigInterfacesIpv4Entry 1 }

gamIpConfigInterfacesIpv4Active OBJECT-TYPE
    SYNTAX      TruthValue
    MAX-ACCESS  read-write
    STATUS      current
    DESCRIPTION
        "Enable IPv4.
         
         IPv4 can only be enabled if either the DHCP client is enabled, or a
         valid address has been configured."
    ::= { gamIpConfigInterfacesIpv4Entry 2 }

gamIpConfigInterfacesIpv4EnableDhcpClient OBJECT-TYPE
    SYNTAX      TruthValue
    MAX-ACCESS  read-write
    STATUS      current
    DESCRIPTION
        "Enable IPv4 DHCP client.
         
         Note: the DHCP client can only be enabled if there is no conflict in
         the values of: ipv4Address, prefixSize, and dhcpClientFallbackTimeout."
    ::= { gamIpConfigInterfacesIpv4Entry 3 }

gamIpConfigInterfacesIpv4Ipv4Address OBJECT-TYPE
    SYNTAX      IpAddress
    MAX-ACCESS  read-write
    STATUS      current
    DESCRIPTION
        "IPv4 address.
         
         Note: Multiple interfaces may not have overlapping networks."
    ::= { gamIpConfigInterfacesIpv4Entry 4 }

gamIpConfigInterfacesIpv4PrefixSize OBJECT-TYPE
    SYNTAX      Unsigned32
    MAX-ACCESS  read-write
    STATUS      current
    DESCRIPTION
        "Prefix size of the network.
         
         Note: Multiple interfaces may not have overlapping networks."
    ::= { gamIpConfigInterfacesIpv4Entry 5 }

gamIpConfigInterfacesIpv4DhcpClientFallbackTimeout OBJECT-TYPE
    SYNTAX      Unsigned32
    MAX-ACCESS  read-write
    STATUS      current
    DESCRIPTION
        "DHCP client fallback timer.
         
         If DHCP is disabled then this object has no effect. If DHCP is enabled
         and the fallback timeout value is different from zero, then this timer
         will stop the DHCP process and assign the ipv4Address to the interface
         instead."
    ::= { gamIpConfigInterfacesIpv4Entry 6 }

gamIpConfigInterfacesIpv4DhcpClientHostname OBJECT-TYPE
    SYNTAX      GAMDisplayString (SIZE(0..63))
    MAX-ACCESS  read-write
    STATUS      current
    DESCRIPTION
        "The hostname of DHCP client. If DHCPv4 client is enabled, the
         configured hostname will be used in the DHCP option 12 field. When this
         value is empty string, the field use the configured system name plus
         the latest three bytes of system MAC addresses as the hostname."
    ::= { gamIpConfigInterfacesIpv4Entry 7 }

gamIpConfigInterfacesIpv4DhcpClientIdType OBJECT-TYPE
    SYNTAX      GAMIpDhcpClientType
    MAX-ACCESS  read-write
    STATUS      current
    DESCRIPTION
        "The type of the DHCP client identifier."
    ::= { gamIpConfigInterfacesIpv4Entry 8 }

gamIpConfigInterfacesIpv4DhcpClientIdIfMac OBJECT-TYPE
    SYNTAX      GAMInterfaceIndex
    MAX-ACCESS  read-write
    STATUS      current
    DESCRIPTION
        "The interface name of DHCP client identifier. When DHCPv4 client is
         enabled and the client identifier type is 'ifmac', the configured
         interface's hardware MAC address will be used in the DHCP option 61
         field."
    ::= { gamIpConfigInterfacesIpv4Entry 9 }

gamIpConfigInterfacesIpv4DhcpClientIdAscii OBJECT-TYPE
    SYNTAX      GAMDisplayString (SIZE(0..31))
    MAX-ACCESS  read-write
    STATUS      current
    DESCRIPTION
        "The ASCII string of DHCP client identifier. When DHCPv4 client is
         enabled and the client identifier type is 'ascii', the ASCII string
         will be used in the DHCP option 61 field."
    ::= { gamIpConfigInterfacesIpv4Entry 10 }

gamIpConfigInterfacesIpv4DhcpClientIdHex OBJECT-TYPE
    SYNTAX      GAMDisplayString (SIZE(0..64))
    MAX-ACCESS  read-write
    STATUS      current
    DESCRIPTION
        "The hexadecimal string of DHCP client identifier. When DHCPv4 client is
         enabled and the client identifier type 'hex', the hexadecimal value
         will be used in the DHCP option 61 field."
    ::= { gamIpConfigInterfacesIpv4Entry 11 }

gamIpConfigInterfacesIpv6Table OBJECT-TYPE
    SYNTAX      SEQUENCE OF GAMIpConfigInterfacesIpv6Entry
    MAX-ACCESS  not-accessible
    STATUS      current
    DESCRIPTION
        "IPv6 interface configuration table. This table enables IPv6 related
         configuration of the corresponding IP interface."
    ::= { gamIpConfigInterfaces 4 }

gamIpConfigInterfacesIpv6Entry OBJECT-TYPE
    SYNTAX      GAMIpConfigInterfacesIpv6Entry
    MAX-ACCESS  not-accessible
    STATUS      current
    DESCRIPTION
        "Each entry in this table represents an IP interface."
    INDEX       { gamIpConfigInterfacesIpv6IfIndex }
    ::= { gamIpConfigInterfacesIpv6Table 1 }

GAMIpConfigInterfacesIpv6Entry ::= SEQUENCE {
    gamIpConfigInterfacesIpv6IfIndex      GAMInterfaceIndex,
    gamIpConfigInterfacesIpv6Active       TruthValue,
    gamIpConfigInterfacesIpv6Ipv6Address  InetAddressIPv6,
    gamIpConfigInterfacesIpv6PrefixSize   Unsigned32
}

gamIpConfigInterfacesIpv6IfIndex OBJECT-TYPE
    SYNTAX      GAMInterfaceIndex
    MAX-ACCESS  accessible-for-notify
    STATUS      current
    DESCRIPTION
        "Interface index number."
    ::= { gamIpConfigInterfacesIpv6Entry 1 }

gamIpConfigInterfacesIpv6Active OBJECT-TYPE
    SYNTAX      TruthValue
    MAX-ACCESS  read-write
    STATUS      current
    DESCRIPTION
        "Enable the static configured IPv6 address.
         
         The static configured IPv6 address can only be configured if a valid
         address has been written into 'ipv6Address' and 'prefixSize'."
    ::= { gamIpConfigInterfacesIpv6Entry 2 }

gamIpConfigInterfacesIpv6Ipv6Address OBJECT-TYPE
    SYNTAX      InetAddressIPv6
    MAX-ACCESS  read-write
    STATUS      current
    DESCRIPTION
        "Static configured IPv6 address."
    ::= { gamIpConfigInterfacesIpv6Entry 3 }

gamIpConfigInterfacesIpv6PrefixSize OBJECT-TYPE
    SYNTAX      Unsigned32
    MAX-ACCESS  read-write
    STATUS      current
    DESCRIPTION
        "Prefix size of the network."
    ::= { gamIpConfigInterfacesIpv6Entry 4 }

gamIpConfigRoutes OBJECT IDENTIFIER
    ::= { gamIpConfig 3 }

gamIpConfigRoutesIpv4Table OBJECT-TYPE
    SYNTAX      SEQUENCE OF GAMIpConfigRoutesIpv4Entry
    MAX-ACCESS  not-accessible
    STATUS      current
    DESCRIPTION
        "This is the IPv4 route configuration table."
    ::= { gamIpConfigRoutes 1 }

gamIpConfigRoutesIpv4Entry OBJECT-TYPE
    SYNTAX      GAMIpConfigRoutesIpv4Entry
    MAX-ACCESS  not-accessible
    STATUS      current
    DESCRIPTION
        "Each entry in this table represents a configured route.
         
         Note: a route may be configured without being active."
    INDEX       { gamIpConfigRoutesIpv4NetworkAddress,
                  gamIpConfigRoutesIpv4NetworkPrefixSize,
                  gamIpConfigRoutesIpv4NextHop }
    ::= { gamIpConfigRoutesIpv4Table 1 }

GAMIpConfigRoutesIpv4Entry ::= SEQUENCE {
    gamIpConfigRoutesIpv4NetworkAddress     IpAddress,
    gamIpConfigRoutesIpv4NetworkPrefixSize  Integer32,
    gamIpConfigRoutesIpv4NextHop            IpAddress,
    gamIpConfigRoutesIpv4Action             GAMRowEditorState
}

gamIpConfigRoutesIpv4NetworkAddress OBJECT-TYPE
    SYNTAX      IpAddress
    MAX-ACCESS  accessible-for-notify
    STATUS      current
    DESCRIPTION
        "Network address."
    ::= { gamIpConfigRoutesIpv4Entry 1 }

gamIpConfigRoutesIpv4NetworkPrefixSize OBJECT-TYPE
    SYNTAX      Integer32 (0..32)
    MAX-ACCESS  accessible-for-notify
    STATUS      current
    DESCRIPTION
        "Network prefix size."
    ::= { gamIpConfigRoutesIpv4Entry 2 }

gamIpConfigRoutesIpv4NextHop OBJECT-TYPE
    SYNTAX      IpAddress
    MAX-ACCESS  accessible-for-notify
    STATUS      current
    DESCRIPTION
        "Next-hop address."
    ::= { gamIpConfigRoutesIpv4Entry 3 }

gamIpConfigRoutesIpv4Action OBJECT-TYPE
    SYNTAX      GAMRowEditorState
    MAX-ACCESS  read-write
    STATUS      current
    DESCRIPTION
        "Action"
    ::= { gamIpConfigRoutesIpv4Entry 100 }

gamIpConfigRoutesIpv4RowEditor OBJECT IDENTIFIER
    ::= { gamIpConfigRoutes 2 }

gamIpConfigRoutesIpv4RowEditorNetworkAddress OBJECT-TYPE
    SYNTAX      IpAddress
    MAX-ACCESS  read-write
    STATUS      current
    DESCRIPTION
        "Network address."
    ::= { gamIpConfigRoutesIpv4RowEditor 1 }

gamIpConfigRoutesIpv4RowEditorNetworkPrefixSize OBJECT-TYPE
    SYNTAX      Integer32 (0..32)
    MAX-ACCESS  read-write
    STATUS      current
    DESCRIPTION
        "Network prefix size."
    ::= { gamIpConfigRoutesIpv4RowEditor 2 }

gamIpConfigRoutesIpv4RowEditorNextHop OBJECT-TYPE
    SYNTAX      IpAddress
    MAX-ACCESS  read-write
    STATUS      current
    DESCRIPTION
        "Next-hop address."
    ::= { gamIpConfigRoutesIpv4RowEditor 3 }

gamIpConfigRoutesIpv4RowEditorAction OBJECT-TYPE
    SYNTAX      GAMRowEditorState
    MAX-ACCESS  read-write
    STATUS      current
    DESCRIPTION
        "Action"
    ::= { gamIpConfigRoutesIpv4RowEditor 100 }

gamIpConfigRoutesIpv6Table OBJECT-TYPE
    SYNTAX      SEQUENCE OF GAMIpConfigRoutesIpv6Entry
    MAX-ACCESS  not-accessible
    STATUS      current
    DESCRIPTION
        "This is the IPv6 route configuration table."
    ::= { gamIpConfigRoutes 3 }

gamIpConfigRoutesIpv6Entry OBJECT-TYPE
    SYNTAX      GAMIpConfigRoutesIpv6Entry
    MAX-ACCESS  not-accessible
    STATUS      current
    DESCRIPTION
        "Each entry in this table represents a configured route.
         
         Note: a route may be configured without being active."
    INDEX       { gamIpConfigRoutesIpv6NetworkAddress,
                  gamIpConfigRoutesIpv6NetworkPrefixSize,
                  gamIpConfigRoutesIpv6NextHop,
                  gamIpConfigRoutesIpv6NextHopInterface }
    ::= { gamIpConfigRoutesIpv6Table 1 }

GAMIpConfigRoutesIpv6Entry ::= SEQUENCE {
    gamIpConfigRoutesIpv6NetworkAddress     InetAddressIPv6,
    gamIpConfigRoutesIpv6NetworkPrefixSize  Integer32,
    gamIpConfigRoutesIpv6NextHop            InetAddressIPv6,
    gamIpConfigRoutesIpv6NextHopInterface   GAMInterfaceIndex,
    gamIpConfigRoutesIpv6Action             GAMRowEditorState
}

gamIpConfigRoutesIpv6NetworkAddress OBJECT-TYPE
    SYNTAX      InetAddressIPv6
    MAX-ACCESS  accessible-for-notify
    STATUS      current
    DESCRIPTION
        "Network address."
    ::= { gamIpConfigRoutesIpv6Entry 1 }

gamIpConfigRoutesIpv6NetworkPrefixSize OBJECT-TYPE
    SYNTAX      Integer32 (0..128)
    MAX-ACCESS  accessible-for-notify
    STATUS      current
    DESCRIPTION
        "Network prefix size."
    ::= { gamIpConfigRoutesIpv6Entry 2 }

gamIpConfigRoutesIpv6NextHop OBJECT-TYPE
    SYNTAX      InetAddressIPv6
    MAX-ACCESS  accessible-for-notify
    STATUS      current
    DESCRIPTION
        "Next-hop address."
    ::= { gamIpConfigRoutesIpv6Entry 3 }

gamIpConfigRoutesIpv6NextHopInterface OBJECT-TYPE
    SYNTAX      GAMInterfaceIndex
    MAX-ACCESS  accessible-for-notify
    STATUS      current
    DESCRIPTION
        "If the next-hop address is a link-local address, then the interface of
         the link-local address must be specified here. Otherwise this value is
         not used."
    ::= { gamIpConfigRoutesIpv6Entry 4 }

gamIpConfigRoutesIpv6Action OBJECT-TYPE
    SYNTAX      GAMRowEditorState
    MAX-ACCESS  read-write
    STATUS      current
    DESCRIPTION
        "Action"
    ::= { gamIpConfigRoutesIpv6Entry 100 }

gamIpConfigRoutesIpv6RowEditor OBJECT IDENTIFIER
    ::= { gamIpConfigRoutes 4 }

gamIpConfigRoutesIpv6RowEditorNetworkAddress OBJECT-TYPE
    SYNTAX      InetAddressIPv6
    MAX-ACCESS  read-write
    STATUS      current
    DESCRIPTION
        "Network address."
    ::= { gamIpConfigRoutesIpv6RowEditor 1 }

gamIpConfigRoutesIpv6RowEditorNetworkPrefixSize OBJECT-TYPE
    SYNTAX      Integer32 (0..128)
    MAX-ACCESS  read-write
    STATUS      current
    DESCRIPTION
        "Network prefix size."
    ::= { gamIpConfigRoutesIpv6RowEditor 2 }

gamIpConfigRoutesIpv6RowEditorNextHop OBJECT-TYPE
    SYNTAX      InetAddressIPv6
    MAX-ACCESS  read-write
    STATUS      current
    DESCRIPTION
        "Next-hop address."
    ::= { gamIpConfigRoutesIpv6RowEditor 3 }

gamIpConfigRoutesIpv6RowEditorNextHopInterface OBJECT-TYPE
    SYNTAX      GAMInterfaceIndex
    MAX-ACCESS  read-write
    STATUS      current
    DESCRIPTION
        "If the next-hop address is a link-local address, then the interface of
         the link-local address must be specified here. Otherwise this value is
         not used."
    ::= { gamIpConfigRoutesIpv6RowEditor 4 }

gamIpConfigRoutesIpv6RowEditorAction OBJECT-TYPE
    SYNTAX      GAMRowEditorState
    MAX-ACCESS  read-write
    STATUS      current
    DESCRIPTION
        "Action"
    ::= { gamIpConfigRoutesIpv6RowEditor 100 }

gamIpStatus OBJECT IDENTIFIER
    ::= { gamIpMibObjects 3 }

gamIpStatusGlobals OBJECT IDENTIFIER
    ::= { gamIpStatus 1 }

gamIpStatusGlobalsIpv4NeighbourTable OBJECT-TYPE
    SYNTAX      SEQUENCE OF GAMIpStatusGlobalsIpv4NeighbourEntry
    MAX-ACCESS  not-accessible
    STATUS      current
    DESCRIPTION
        "This is the IPv4 neighbour table (ARP)."
    ::= { gamIpStatusGlobals 1 }

gamIpStatusGlobalsIpv4NeighbourEntry OBJECT-TYPE
    SYNTAX      GAMIpStatusGlobalsIpv4NeighbourEntry
    MAX-ACCESS  not-accessible
    STATUS      current
    DESCRIPTION
        "Each entry in this table represents an entry in the underlying operting
         system's ARP table."
    INDEX       { gamIpStatusGlobalsIpv4NeighbourIpv4 }
    ::= { gamIpStatusGlobalsIpv4NeighbourTable 1 }

GAMIpStatusGlobalsIpv4NeighbourEntry ::= SEQUENCE {
    gamIpStatusGlobalsIpv4NeighbourIpv4        IpAddress,
    gamIpStatusGlobalsIpv4NeighbourMacAddress  MacAddress,
    gamIpStatusGlobalsIpv4NeighbourInterface   GAMInterfaceIndex
}

gamIpStatusGlobalsIpv4NeighbourIpv4 OBJECT-TYPE
    SYNTAX      IpAddress
    MAX-ACCESS  accessible-for-notify
    STATUS      current
    DESCRIPTION
        "IPv4 address."
    ::= { gamIpStatusGlobalsIpv4NeighbourEntry 1 }

gamIpStatusGlobalsIpv4NeighbourMacAddress OBJECT-TYPE
    SYNTAX      MacAddress
    MAX-ACCESS  read-only
    STATUS      current
    DESCRIPTION
        "MAC address associated with the IP address"
    ::= { gamIpStatusGlobalsIpv4NeighbourEntry 2 }

gamIpStatusGlobalsIpv4NeighbourInterface OBJECT-TYPE
    SYNTAX      GAMInterfaceIndex
    MAX-ACCESS  read-only
    STATUS      current
    DESCRIPTION
        "Interface the neighbour can be reached on."
    ::= { gamIpStatusGlobalsIpv4NeighbourEntry 3 }

gamIpStatusGlobalsIpv6NeighbourTable OBJECT-TYPE
    SYNTAX      SEQUENCE OF GAMIpStatusGlobalsIpv6NeighbourEntry
    MAX-ACCESS  not-accessible
    STATUS      current
    DESCRIPTION
        "This is the IPv6 neighbour table."
    ::= { gamIpStatusGlobals 2 }

gamIpStatusGlobalsIpv6NeighbourEntry OBJECT-TYPE
    SYNTAX      GAMIpStatusGlobalsIpv6NeighbourEntry
    MAX-ACCESS  not-accessible
    STATUS      current
    DESCRIPTION
        "Each entry in this table represents an entry in the underlying operting
         system's nieghbour table."
    INDEX       { gamIpStatusGlobalsIpv6NeighbourIpAddress,
                  gamIpStatusGlobalsIpv6NeighbourInterfaceQuery }
    ::= { gamIpStatusGlobalsIpv6NeighbourTable 1 }

GAMIpStatusGlobalsIpv6NeighbourEntry ::= SEQUENCE {
    gamIpStatusGlobalsIpv6NeighbourIpAddress       InetAddressIPv6,
    gamIpStatusGlobalsIpv6NeighbourInterfaceQuery  Integer32,
    gamIpStatusGlobalsIpv6NeighbourMacAddress      MacAddress,
    gamIpStatusGlobalsIpv6NeighbourInterface       GAMInterfaceIndex
}

gamIpStatusGlobalsIpv6NeighbourIpAddress OBJECT-TYPE
    SYNTAX      InetAddressIPv6
    MAX-ACCESS  accessible-for-notify
    STATUS      current
    DESCRIPTION
        "IP address."
    ::= { gamIpStatusGlobalsIpv6NeighbourEntry 1 }

gamIpStatusGlobalsIpv6NeighbourInterfaceQuery OBJECT-TYPE
    SYNTAX      Integer32 (0..2147483647)
    MAX-ACCESS  accessible-for-notify
    STATUS      current
    DESCRIPTION
        "If 'ipAddress' is a link-local address, then the interface index where
         the host can be reached must be specified here, otherwise set this to
         zero."
    ::= { gamIpStatusGlobalsIpv6NeighbourEntry 2 }

gamIpStatusGlobalsIpv6NeighbourMacAddress OBJECT-TYPE
    SYNTAX      MacAddress
    MAX-ACCESS  read-only
    STATUS      current
    DESCRIPTION
        "MAC address associated with the IP address"
    ::= { gamIpStatusGlobalsIpv6NeighbourEntry 3 }

gamIpStatusGlobalsIpv6NeighbourInterface OBJECT-TYPE
    SYNTAX      GAMInterfaceIndex
    MAX-ACCESS  read-only
    STATUS      current
    DESCRIPTION
        "Interface the neighbour can be reached on."
    ::= { gamIpStatusGlobalsIpv6NeighbourEntry 4 }

gamIpStatusInterfaces OBJECT IDENTIFIER
    ::= { gamIpStatus 2 }

gamIpStatusInterfacesLinkTable OBJECT-TYPE
    SYNTAX      SEQUENCE OF GAMIpStatusInterfacesLinkEntry
    MAX-ACCESS  not-accessible
    STATUS      current
    DESCRIPTION
        "This table provides link-layer status information for IP interfaces."
    ::= { gamIpStatusInterfaces 1 }

gamIpStatusInterfacesLinkEntry OBJECT-TYPE
    SYNTAX      GAMIpStatusInterfacesLinkEntry
    MAX-ACCESS  not-accessible
    STATUS      current
    DESCRIPTION
        "Each entry in this table represents an IP interface."
    INDEX       { gamIpStatusInterfacesLinkIfIndex }
    ::= { gamIpStatusInterfacesLinkTable 1 }

GAMIpStatusInterfacesLinkEntry ::= SEQUENCE {
    gamIpStatusInterfacesLinkIfIndex           GAMInterfaceIndex,
    gamIpStatusInterfacesLinkOsInterfaceIndex  Unsigned32,
    gamIpStatusInterfacesLinkMtu               Unsigned32,
    gamIpStatusInterfacesLinkMacAddress        MacAddress,
    gamIpStatusInterfacesLinkUp                TruthValue,
    gamIpStatusInterfacesLinkBroadcast         TruthValue,
    gamIpStatusInterfacesLinkLoopback          TruthValue,
    gamIpStatusInterfacesLinkRunning           TruthValue,
    gamIpStatusInterfacesLinkNoarp             TruthValue,
    gamIpStatusInterfacesLinkPromisc           TruthValue,
    gamIpStatusInterfacesLinkMulticast         TruthValue
}

gamIpStatusInterfacesLinkIfIndex OBJECT-TYPE
    SYNTAX      GAMInterfaceIndex
    MAX-ACCESS  accessible-for-notify
    STATUS      current
    DESCRIPTION
        "Interface index number."
    ::= { gamIpStatusInterfacesLinkEntry 1 }

gamIpStatusInterfacesLinkOsInterfaceIndex OBJECT-TYPE
    SYNTAX      Unsigned32
    MAX-ACCESS  read-only
    STATUS      current
    DESCRIPTION
        "Interface index used by the operating system."
    ::= { gamIpStatusInterfacesLinkEntry 2 }

gamIpStatusInterfacesLinkMtu OBJECT-TYPE
    SYNTAX      Unsigned32
    MAX-ACCESS  read-only
    STATUS      current
    DESCRIPTION
        "MTU for the interface."
    ::= { gamIpStatusInterfacesLinkEntry 3 }

gamIpStatusInterfacesLinkMacAddress OBJECT-TYPE
    SYNTAX      MacAddress
    MAX-ACCESS  read-only
    STATUS      current
    DESCRIPTION
        "MAC-address of the interface."
    ::= { gamIpStatusInterfacesLinkEntry 4 }

gamIpStatusInterfacesLinkUp OBJECT-TYPE
    SYNTAX      TruthValue
    MAX-ACCESS  read-only
    STATUS      current
    DESCRIPTION
        "Indicates if the interface is up."
    ::= { gamIpStatusInterfacesLinkEntry 5 }

gamIpStatusInterfacesLinkBroadcast OBJECT-TYPE
    SYNTAX      TruthValue
    MAX-ACCESS  read-only
    STATUS      current
    DESCRIPTION
        "Indicates if the interface is capable of transmitting broadcast
         traffic."
    ::= { gamIpStatusInterfacesLinkEntry 6 }

gamIpStatusInterfacesLinkLoopback OBJECT-TYPE
    SYNTAX      TruthValue
    MAX-ACCESS  read-only
    STATUS      current
    DESCRIPTION
        "Indicates if the interface is a loop-back interface."
    ::= { gamIpStatusInterfacesLinkEntry 7 }

gamIpStatusInterfacesLinkRunning OBJECT-TYPE
    SYNTAX      TruthValue
    MAX-ACCESS  read-only
    STATUS      current
    DESCRIPTION
        "Interface is running (according to the operating system)."
    ::= { gamIpStatusInterfacesLinkEntry 8 }

gamIpStatusInterfacesLinkNoarp OBJECT-TYPE
    SYNTAX      TruthValue
    MAX-ACCESS  read-only
    STATUS      current
    DESCRIPTION
        "Indicates if the interface will answer to ARP requests."
    ::= { gamIpStatusInterfacesLinkEntry 9 }

gamIpStatusInterfacesLinkPromisc OBJECT-TYPE
    SYNTAX      TruthValue
    MAX-ACCESS  read-only
    STATUS      current
    DESCRIPTION
        "Indicates if the interface is in promisc mode."
    ::= { gamIpStatusInterfacesLinkEntry 10 }

gamIpStatusInterfacesLinkMulticast OBJECT-TYPE
    SYNTAX      TruthValue
    MAX-ACCESS  read-only
    STATUS      current
    DESCRIPTION
        "Indicates if the interface supports multicast."
    ::= { gamIpStatusInterfacesLinkEntry 11 }

gamIpStatusInterfacesIpv4Table OBJECT-TYPE
    SYNTAX      SEQUENCE OF GAMIpStatusInterfacesIpv4Entry
    MAX-ACCESS  not-accessible
    STATUS      current
    DESCRIPTION
        "This table provides IPv4 status information for IP interfaces. If an
         interface is configured to use a DHCP client, then the address can be
         found here."
    ::= { gamIpStatusInterfaces 2 }

gamIpStatusInterfacesIpv4Entry OBJECT-TYPE
    SYNTAX      GAMIpStatusInterfacesIpv4Entry
    MAX-ACCESS  not-accessible
    STATUS      current
    DESCRIPTION
        "Each entry in this table represents an IP interface."
    INDEX       { gamIpStatusInterfacesIpv4IfIndex,
                  gamIpStatusInterfacesIpv4NetworkAddress,
                  gamIpStatusInterfacesIpv4NetworkMaskLength }
    ::= { gamIpStatusInterfacesIpv4Table 1 }

GAMIpStatusInterfacesIpv4Entry ::= SEQUENCE {
    gamIpStatusInterfacesIpv4IfIndex            GAMInterfaceIndex,
    gamIpStatusInterfacesIpv4NetworkAddress     IpAddress,
    gamIpStatusInterfacesIpv4NetworkMaskLength  Integer32,
    gamIpStatusInterfacesIpv4Broadcast          IpAddress
}

gamIpStatusInterfacesIpv4IfIndex OBJECT-TYPE
    SYNTAX      GAMInterfaceIndex
    MAX-ACCESS  accessible-for-notify
    STATUS      current
    DESCRIPTION
        "Interface index number."
    ::= { gamIpStatusInterfacesIpv4Entry 1 }

gamIpStatusInterfacesIpv4NetworkAddress OBJECT-TYPE
    SYNTAX      IpAddress
    MAX-ACCESS  accessible-for-notify
    STATUS      current
    DESCRIPTION
        "IPv4 network address."
    ::= { gamIpStatusInterfacesIpv4Entry 2 }

gamIpStatusInterfacesIpv4NetworkMaskLength OBJECT-TYPE
    SYNTAX      Integer32 (0..32)
    MAX-ACCESS  accessible-for-notify
    STATUS      current
    DESCRIPTION
        "IPv4 network mask length."
    ::= { gamIpStatusInterfacesIpv4Entry 3 }

gamIpStatusInterfacesIpv4Broadcast OBJECT-TYPE
    SYNTAX      IpAddress
    MAX-ACCESS  read-only
    STATUS      current
    DESCRIPTION
        "Broadcast address."
    ::= { gamIpStatusInterfacesIpv4Entry 4 }

gamIpStatusInterfacesDhcpClientV4Table OBJECT-TYPE
    SYNTAX      SEQUENCE OF GAMIpStatusInterfacesDhcpClientV4Entry
    MAX-ACCESS  not-accessible
    STATUS      current
    DESCRIPTION
        "This table provides status on the DHCP client running on a given
         interface."
    ::= { gamIpStatusInterfaces 3 }

gamIpStatusInterfacesDhcpClientV4Entry OBJECT-TYPE
    SYNTAX      GAMIpStatusInterfacesDhcpClientV4Entry
    MAX-ACCESS  not-accessible
    STATUS      current
    DESCRIPTION
        "Each entry in this table represents an instance of a DHCP client."
    INDEX       { gamIpStatusInterfacesDhcpClientV4IfIndex }
    ::= { gamIpStatusInterfacesDhcpClientV4Table 1 }

GAMIpStatusInterfacesDhcpClientV4Entry ::= SEQUENCE {
    gamIpStatusInterfacesDhcpClientV4IfIndex   GAMInterfaceIndex,
    gamIpStatusInterfacesDhcpClientV4State     GAMIpDhcpClientState,
    gamIpStatusInterfacesDhcpClientV4ServerIp  IpAddress
}

gamIpStatusInterfacesDhcpClientV4IfIndex OBJECT-TYPE
    SYNTAX      GAMInterfaceIndex
    MAX-ACCESS  accessible-for-notify
    STATUS      current
    DESCRIPTION
        "Interface index number."
    ::= { gamIpStatusInterfacesDhcpClientV4Entry 1 }

gamIpStatusInterfacesDhcpClientV4State OBJECT-TYPE
    SYNTAX      GAMIpDhcpClientState
    MAX-ACCESS  read-only
    STATUS      current
    DESCRIPTION
        "State of the DHCP client."
    ::= { gamIpStatusInterfacesDhcpClientV4Entry 2 }

gamIpStatusInterfacesDhcpClientV4ServerIp OBJECT-TYPE
    SYNTAX      IpAddress
    MAX-ACCESS  read-only
    STATUS      current
    DESCRIPTION
        "IP address of the DHCP server that has provided the DHCP offer."
    ::= { gamIpStatusInterfacesDhcpClientV4Entry 3 }

gamIpStatusInterfacesIpv6Table OBJECT-TYPE
    SYNTAX      SEQUENCE OF GAMIpStatusInterfacesIpv6Entry
    MAX-ACCESS  not-accessible
    STATUS      current
    DESCRIPTION
        "This table provides IPv6 status information for IP interfaces. If an
         interface is configured to use a DHCP client, then the address can be
         found here."
    ::= { gamIpStatusInterfaces 4 }

gamIpStatusInterfacesIpv6Entry OBJECT-TYPE
    SYNTAX      GAMIpStatusInterfacesIpv6Entry
    MAX-ACCESS  not-accessible
    STATUS      current
    DESCRIPTION
        "Each entry in this table represents an IP interface."
    INDEX       { gamIpStatusInterfacesIpv6IfIndex,
                  gamIpStatusInterfacesIpv6NetworkAddress,
                  gamIpStatusInterfacesIpv6NetworkMaskLength }
    ::= { gamIpStatusInterfacesIpv6Table 1 }

GAMIpStatusInterfacesIpv6Entry ::= SEQUENCE {
    gamIpStatusInterfacesIpv6IfIndex            GAMInterfaceIndex,
    gamIpStatusInterfacesIpv6NetworkAddress     InetAddressIPv6,
    gamIpStatusInterfacesIpv6NetworkMaskLength  Integer32,
    gamIpStatusInterfacesIpv6Tentative          TruthValue,
    gamIpStatusInterfacesIpv6Duplicated         TruthValue,
    gamIpStatusInterfacesIpv6Detached           TruthValue,
    gamIpStatusInterfacesIpv6Nodad              TruthValue,
    gamIpStatusInterfacesIpv6Autoconf           TruthValue
}

gamIpStatusInterfacesIpv6IfIndex OBJECT-TYPE
    SYNTAX      GAMInterfaceIndex
    MAX-ACCESS  accessible-for-notify
    STATUS      current
    DESCRIPTION
        "Interface index number."
    ::= { gamIpStatusInterfacesIpv6Entry 1 }

gamIpStatusInterfacesIpv6NetworkAddress OBJECT-TYPE
    SYNTAX      InetAddressIPv6
    MAX-ACCESS  accessible-for-notify
    STATUS      current
    DESCRIPTION
        "IPv6 network address."
    ::= { gamIpStatusInterfacesIpv6Entry 2 }

gamIpStatusInterfacesIpv6NetworkMaskLength OBJECT-TYPE
    SYNTAX      Integer32 (0..128)
    MAX-ACCESS  accessible-for-notify
    STATUS      current
    DESCRIPTION
        "IPv6 network mask length."
    ::= { gamIpStatusInterfacesIpv6Entry 3 }

gamIpStatusInterfacesIpv6Tentative OBJECT-TYPE
    SYNTAX      TruthValue
    MAX-ACCESS  read-only
    STATUS      current
    DESCRIPTION
        "An address whose uniqueness on a link is being verified, prior to its
         assignment to an interface. A tentative address is not considered
         assigned to an interface in the usual sense."
    ::= { gamIpStatusInterfacesIpv6Entry 4 }

gamIpStatusInterfacesIpv6Duplicated OBJECT-TYPE
    SYNTAX      TruthValue
    MAX-ACCESS  read-only
    STATUS      current
    DESCRIPTION
        "Indicates the address duplication is detected by Duplicate Address
         Detection (DAD).
         
         If the address is a link-local address formed from an interface
         identifier based on the hardware address, which is supposed to be
         uniquely assigned (e.g., EUI-64 for an Ethernet interface), IP
         operation on the interface should be disabled."
    ::= { gamIpStatusInterfacesIpv6Entry 5 }

gamIpStatusInterfacesIpv6Detached OBJECT-TYPE
    SYNTAX      TruthValue
    MAX-ACCESS  read-only
    STATUS      current
    DESCRIPTION
        "Indicates this address is ready to be detached from the link (IPv6
         network)."
    ::= { gamIpStatusInterfacesIpv6Entry 6 }

gamIpStatusInterfacesIpv6Nodad OBJECT-TYPE
    SYNTAX      TruthValue
    MAX-ACCESS  read-only
    STATUS      current
    DESCRIPTION
        "Indicates this address does not perform Duplicate Address Detection
         (DAD)."
    ::= { gamIpStatusInterfacesIpv6Entry 7 }

gamIpStatusInterfacesIpv6Autoconf OBJECT-TYPE
    SYNTAX      TruthValue
    MAX-ACCESS  read-only
    STATUS      current
    DESCRIPTION
        "Indicates this address is capable of being retrieved by stateless
         address autoconfiguration."
    ::= { gamIpStatusInterfacesIpv6Entry 8 }

gamIpStatusRoutes OBJECT IDENTIFIER
    ::= { gamIpStatus 3 }

gamIpStatusRoutesIpv4Table OBJECT-TYPE
    SYNTAX      SEQUENCE OF GAMIpStatusRoutesIpv4Entry
    MAX-ACCESS  not-accessible
    STATUS      current
    DESCRIPTION
        "This table provides IPv4 routing status."
    ::= { gamIpStatusRoutes 1 }

gamIpStatusRoutesIpv4Entry OBJECT-TYPE
    SYNTAX      GAMIpStatusRoutesIpv4Entry
    MAX-ACCESS  not-accessible
    STATUS      current
    DESCRIPTION
        "Each entry in this table represents an IP route in the system's routing
         table."
    INDEX       { gamIpStatusRoutesIpv4NetworkAddress,
                  gamIpStatusRoutesIpv4NetworkPrefixSize,
                  gamIpStatusRoutesIpv4NextHop }
    ::= { gamIpStatusRoutesIpv4Table 1 }

GAMIpStatusRoutesIpv4Entry ::= SEQUENCE {
    gamIpStatusRoutesIpv4NetworkAddress           IpAddress,
    gamIpStatusRoutesIpv4NetworkPrefixSize        Integer32,
    gamIpStatusRoutesIpv4NextHop                  IpAddress,
    gamIpStatusRoutesIpv4DerivedNextHopInterface  GAMInterfaceIndex,
    gamIpStatusRoutesIpv4FlagUp                   TruthValue,
    gamIpStatusRoutesIpv4FlagHost                 TruthValue,
    gamIpStatusRoutesIpv4FlagGateway              TruthValue,
    gamIpStatusRoutesIpv4OwnerConf                TruthValue,
    gamIpStatusRoutesIpv4OwnerDhcp                TruthValue,
    gamIpStatusRoutesIpv4OwnerDynamic             TruthValue
}

gamIpStatusRoutesIpv4NetworkAddress OBJECT-TYPE
    SYNTAX      IpAddress
    MAX-ACCESS  accessible-for-notify
    STATUS      current
    DESCRIPTION
        "Network address."
    ::= { gamIpStatusRoutesIpv4Entry 1 }

gamIpStatusRoutesIpv4NetworkPrefixSize OBJECT-TYPE
    SYNTAX      Integer32 (0..32)
    MAX-ACCESS  accessible-for-notify
    STATUS      current
    DESCRIPTION
        "Network prefix size."
    ::= { gamIpStatusRoutesIpv4Entry 2 }

gamIpStatusRoutesIpv4NextHop OBJECT-TYPE
    SYNTAX      IpAddress
    MAX-ACCESS  accessible-for-notify
    STATUS      current
    DESCRIPTION
        "Next-hop address."
    ::= { gamIpStatusRoutesIpv4Entry 3 }

gamIpStatusRoutesIpv4DerivedNextHopInterface OBJECT-TYPE
    SYNTAX      GAMInterfaceIndex
    MAX-ACCESS  read-only
    STATUS      current
    DESCRIPTION
        "Next-hop interface."
    ::= { gamIpStatusRoutesIpv4Entry 4 }

gamIpStatusRoutesIpv4FlagUp OBJECT-TYPE
    SYNTAX      TruthValue
    MAX-ACCESS  read-only
    STATUS      current
    DESCRIPTION
        "The route is up."
    ::= { gamIpStatusRoutesIpv4Entry 35 }

gamIpStatusRoutesIpv4FlagHost OBJECT-TYPE
    SYNTAX      TruthValue
    MAX-ACCESS  read-only
    STATUS      current
    DESCRIPTION
        "The route is forwarding to this host (loop-back)."
    ::= { gamIpStatusRoutesIpv4Entry 36 }

gamIpStatusRoutesIpv4FlagGateway OBJECT-TYPE
    SYNTAX      TruthValue
    MAX-ACCESS  read-only
    STATUS      current
    DESCRIPTION
        "The route is using a gateway as next-hop, of not set then an interface
         is used."
    ::= { gamIpStatusRoutesIpv4Entry 37 }

gamIpStatusRoutesIpv4OwnerConf OBJECT-TYPE
    SYNTAX      TruthValue
    MAX-ACCESS  read-only
    STATUS      current
    DESCRIPTION
        "The route is installed as part of the user configuration."
    ::= { gamIpStatusRoutesIpv4Entry 67 }

gamIpStatusRoutesIpv4OwnerDhcp OBJECT-TYPE
    SYNTAX      TruthValue
    MAX-ACCESS  read-only
    STATUS      current
    DESCRIPTION
        "The route is installed by a DHCP client."
    ::= { gamIpStatusRoutesIpv4Entry 68 }

gamIpStatusRoutesIpv4OwnerDynamic OBJECT-TYPE
    SYNTAX      TruthValue
    MAX-ACCESS  read-only
    STATUS      current
    DESCRIPTION
        "The route is installed by a routing protocol."
    ::= { gamIpStatusRoutesIpv4Entry 69 }

gamIpStatusRoutesIpv6Table OBJECT-TYPE
    SYNTAX      SEQUENCE OF GAMIpStatusRoutesIpv6Entry
    MAX-ACCESS  not-accessible
    STATUS      current
    DESCRIPTION
        "This table provides IPv6 routing status."
    ::= { gamIpStatusRoutes 2 }

gamIpStatusRoutesIpv6Entry OBJECT-TYPE
    SYNTAX      GAMIpStatusRoutesIpv6Entry
    MAX-ACCESS  not-accessible
    STATUS      current
    DESCRIPTION
        "Each entry in this table represents an IP route in the system's routing
         table."
    INDEX       { gamIpStatusRoutesIpv6NetworkAddress,
                  gamIpStatusRoutesIpv6NetworkPrefixSize,
                  gamIpStatusRoutesIpv6NextHop,
                  gamIpStatusRoutesIpv6NextHopInterface }
    ::= { gamIpStatusRoutesIpv6Table 1 }

GAMIpStatusRoutesIpv6Entry ::= SEQUENCE {
    gamIpStatusRoutesIpv6NetworkAddress           InetAddressIPv6,
    gamIpStatusRoutesIpv6NetworkPrefixSize        Integer32,
    gamIpStatusRoutesIpv6NextHop                  InetAddressIPv6,
    gamIpStatusRoutesIpv6NextHopInterface         GAMInterfaceIndex,
    gamIpStatusRoutesIpv6DerivedNextHopInterface  GAMInterfaceIndex,
    gamIpStatusRoutesIpv6FlagUp                   TruthValue,
    gamIpStatusRoutesIpv6FlagHost                 TruthValue,
    gamIpStatusRoutesIpv6FlagGateway              TruthValue,
    gamIpStatusRoutesIpv6OwnerConf                TruthValue,
    gamIpStatusRoutesIpv6OwnerDhcp                TruthValue,
    gamIpStatusRoutesIpv6OwnerDynamic             TruthValue
}

gamIpStatusRoutesIpv6NetworkAddress OBJECT-TYPE
    SYNTAX      InetAddressIPv6
    MAX-ACCESS  accessible-for-notify
    STATUS      current
    DESCRIPTION
        "Network address."
    ::= { gamIpStatusRoutesIpv6Entry 1 }

gamIpStatusRoutesIpv6NetworkPrefixSize OBJECT-TYPE
    SYNTAX      Integer32 (0..128)
    MAX-ACCESS  accessible-for-notify
    STATUS      current
    DESCRIPTION
        "Network prefix size."
    ::= { gamIpStatusRoutesIpv6Entry 2 }

gamIpStatusRoutesIpv6NextHop OBJECT-TYPE
    SYNTAX      InetAddressIPv6
    MAX-ACCESS  accessible-for-notify
    STATUS      current
    DESCRIPTION
        "Next-hop address."
    ::= { gamIpStatusRoutesIpv6Entry 3 }

gamIpStatusRoutesIpv6NextHopInterface OBJECT-TYPE
    SYNTAX      GAMInterfaceIndex
    MAX-ACCESS  accessible-for-notify
    STATUS      current
    DESCRIPTION
        "If the next-hop address is a link-local address, then the interface of
         the link-local address must be specified here. Otherwise this value is
         not used."
    ::= { gamIpStatusRoutesIpv6Entry 4 }

gamIpStatusRoutesIpv6DerivedNextHopInterface OBJECT-TYPE
    SYNTAX      GAMInterfaceIndex
    MAX-ACCESS  read-only
    STATUS      current
    DESCRIPTION
        "Next-hop interface."
    ::= { gamIpStatusRoutesIpv6Entry 5 }

gamIpStatusRoutesIpv6FlagUp OBJECT-TYPE
    SYNTAX      TruthValue
    MAX-ACCESS  read-only
    STATUS      current
    DESCRIPTION
        "The route is up."
    ::= { gamIpStatusRoutesIpv6Entry 36 }

gamIpStatusRoutesIpv6FlagHost OBJECT-TYPE
    SYNTAX      TruthValue
    MAX-ACCESS  read-only
    STATUS      current
    DESCRIPTION
        "The route is forwarding to this host (loop-back)."
    ::= { gamIpStatusRoutesIpv6Entry 37 }

gamIpStatusRoutesIpv6FlagGateway OBJECT-TYPE
    SYNTAX      TruthValue
    MAX-ACCESS  read-only
    STATUS      current
    DESCRIPTION
        "The route is using a gateway as next-hop, of not set then an interface
         is used."
    ::= { gamIpStatusRoutesIpv6Entry 38 }

gamIpStatusRoutesIpv6OwnerConf OBJECT-TYPE
    SYNTAX      TruthValue
    MAX-ACCESS  read-only
    STATUS      current
    DESCRIPTION
        "The route is installed as part of the user configuration."
    ::= { gamIpStatusRoutesIpv6Entry 68 }

gamIpStatusRoutesIpv6OwnerDhcp OBJECT-TYPE
    SYNTAX      TruthValue
    MAX-ACCESS  read-only
    STATUS      current
    DESCRIPTION
        "The route is installed by a DHCP client."
    ::= { gamIpStatusRoutesIpv6Entry 69 }

gamIpStatusRoutesIpv6OwnerDynamic OBJECT-TYPE
    SYNTAX      TruthValue
    MAX-ACCESS  read-only
    STATUS      current
    DESCRIPTION
        "The route is installed by a routing protocol."
    ::= { gamIpStatusRoutesIpv6Entry 70 }

gamIpControl OBJECT IDENTIFIER
    ::= { gamIpMibObjects 4 }

gamIpControlGlobals OBJECT IDENTIFIER
    ::= { gamIpControl 1 }

gamIpControlGlobalsIpv4NeighbourTableClear OBJECT-TYPE
    SYNTAX      TruthValue
    MAX-ACCESS  read-write
    STATUS      current
    DESCRIPTION
        "Flush the entries in IPv4 ARP cache except for the permanent ones."
    ::= { gamIpControlGlobals 1 }

gamIpControlGlobalsIpv6NeighbourTableClear OBJECT-TYPE
    SYNTAX      TruthValue
    MAX-ACCESS  read-write
    STATUS      current
    DESCRIPTION
        "Erase all the NDP (Neighbor Discovery Protocol) entries registered in
         IPv6 neighbour cache."
    ::= { gamIpControlGlobals 2 }

gamIpControlGlobalsIpv4SystemStatisticsClear OBJECT-TYPE
    SYNTAX      GAMUnsigned8
    MAX-ACCESS  read-write
    STATUS      current
    DESCRIPTION
        "Clear the system-wide IPv4 traffic statistics."
    ::= { gamIpControlGlobals 3 }

gamIpControlGlobalsIpv6SystemStatisticsClear OBJECT-TYPE
    SYNTAX      GAMUnsigned8
    MAX-ACCESS  read-write
    STATUS      current
    DESCRIPTION
        "Clear the system-wide IPv6 traffic statistics."
    ::= { gamIpControlGlobals 4 }

gamIpControlGlobalsIpv4AcdStatusClear OBJECT-TYPE
    SYNTAX      GAMUnsigned8
    MAX-ACCESS  read-write
    STATUS      current
    DESCRIPTION
        "Clear the Address Conflict Detection table."
    ::= { gamIpControlGlobals 5 }

gamIpControlInterface OBJECT IDENTIFIER
    ::= { gamIpControl 2 }

gamIpControlInterfaceDhcpClientTable OBJECT-TYPE
    SYNTAX      SEQUENCE OF GAMIpControlInterfaceDhcpClientEntry
    MAX-ACCESS  not-accessible
    STATUS      current
    DESCRIPTION
        "This table provides control facilities to control an instance of the
         DHCP client."
    ::= { gamIpControlInterface 1 }

gamIpControlInterfaceDhcpClientEntry OBJECT-TYPE
    SYNTAX      GAMIpControlInterfaceDhcpClientEntry
    MAX-ACCESS  not-accessible
    STATUS      current
    DESCRIPTION
        "Each entry in this table represents an instance of the DHCP client."
    INDEX       { gamIpControlInterfaceDhcpClientIfIndex }
    ::= { gamIpControlInterfaceDhcpClientTable 1 }

GAMIpControlInterfaceDhcpClientEntry ::= SEQUENCE {
    gamIpControlInterfaceDhcpClientIfIndex  GAMInterfaceIndex,
    gamIpControlInterfaceDhcpClientRestart  TruthValue
}

gamIpControlInterfaceDhcpClientIfIndex OBJECT-TYPE
    SYNTAX      GAMInterfaceIndex
    MAX-ACCESS  accessible-for-notify
    STATUS      current
    DESCRIPTION
        "Interface index number."
    ::= { gamIpControlInterfaceDhcpClientEntry 1 }

gamIpControlInterfaceDhcpClientRestart OBJECT-TYPE
    SYNTAX      TruthValue
    MAX-ACCESS  read-write
    STATUS      current
    DESCRIPTION
        "Restart the DHCP client."
    ::= { gamIpControlInterfaceDhcpClientEntry 2 }

gamIpStatistics OBJECT IDENTIFIER
    ::= { gamIpMibObjects 5 }

gamIpStatisticsGlobals OBJECT IDENTIFIER
    ::= { gamIpStatistics 1 }

gamIpStatisticsGlobalsIpv4 OBJECT IDENTIFIER
    ::= { gamIpStatisticsGlobals 1 }

gamIpStatisticsGlobalsIpv4InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime."
    ::= { gamIpStatisticsGlobalsIpv4 1 }

gamIpStatisticsGlobalsIpv4HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime."
    ::= { gamIpStatisticsGlobalsIpv4 2 }

gamIpStatisticsGlobalsIpv4InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime."
    ::= { gamIpStatisticsGlobalsIpv4 3 }

gamIpStatisticsGlobalsIpv4HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime."
    ::= { gamIpStatisticsGlobalsIpv4 4 }

gamIpStatisticsGlobalsIpv4InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime."
    ::= { gamIpStatisticsGlobalsIpv4 5 }

gamIpStatisticsGlobalsIpv4InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime."
    ::= { gamIpStatisticsGlobalsIpv4 6 }

gamIpStatisticsGlobalsIpv4InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime."
    ::= { gamIpStatisticsGlobalsIpv4 7 }

gamIpStatisticsGlobalsIpv4InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { gamIpStatisticsGlobalsIpv4 8 }

gamIpStatisticsGlobalsIpv4InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime."
    ::= { gamIpStatisticsGlobalsIpv4 9 }

gamIpStatisticsGlobalsIpv4InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime."
    ::= { gamIpStatisticsGlobalsIpv4 10 }

gamIpStatisticsGlobalsIpv4HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime."
    ::= { gamIpStatisticsGlobalsIpv4 11 }

gamIpStatisticsGlobalsIpv4ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime."
    ::= { gamIpStatisticsGlobalsIpv4 12 }

gamIpStatisticsGlobalsIpv4ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { gamIpStatisticsGlobalsIpv4 13 }

gamIpStatisticsGlobalsIpv4ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime."
    ::= { gamIpStatisticsGlobalsIpv4 14 }

gamIpStatisticsGlobalsIpv4InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime."
    ::= { gamIpStatisticsGlobalsIpv4 15 }

gamIpStatisticsGlobalsIpv4InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { gamIpStatisticsGlobalsIpv4 16 }

gamIpStatisticsGlobalsIpv4HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime."
    ::= { gamIpStatisticsGlobalsIpv4 17 }

gamIpStatisticsGlobalsIpv4OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime."
    ::= { gamIpStatisticsGlobalsIpv4 18 }

gamIpStatisticsGlobalsIpv4HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime."
    ::= { gamIpStatisticsGlobalsIpv4 19 }

gamIpStatisticsGlobalsIpv4OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime."
    ::= { gamIpStatisticsGlobalsIpv4 20 }

gamIpStatisticsGlobalsIpv4OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime."
    ::= { gamIpStatisticsGlobalsIpv4 21 }

gamIpStatisticsGlobalsIpv4HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime."
    ::= { gamIpStatisticsGlobalsIpv4 22 }

gamIpStatisticsGlobalsIpv4OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime."
    ::= { gamIpStatisticsGlobalsIpv4 23 }

gamIpStatisticsGlobalsIpv4OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime."
    ::= { gamIpStatisticsGlobalsIpv4 24 }

gamIpStatisticsGlobalsIpv4OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime."
    ::= { gamIpStatisticsGlobalsIpv4 25 }

gamIpStatisticsGlobalsIpv4OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime."
    ::= { gamIpStatisticsGlobalsIpv4 26 }

gamIpStatisticsGlobalsIpv4OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime."
    ::= { gamIpStatisticsGlobalsIpv4 27 }

gamIpStatisticsGlobalsIpv4OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime."
    ::= { gamIpStatisticsGlobalsIpv4 28 }

gamIpStatisticsGlobalsIpv4HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime."
    ::= { gamIpStatisticsGlobalsIpv4 29 }

gamIpStatisticsGlobalsIpv4OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime."
    ::= { gamIpStatisticsGlobalsIpv4 30 }

gamIpStatisticsGlobalsIpv4HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime."
    ::= { gamIpStatisticsGlobalsIpv4 31 }

gamIpStatisticsGlobalsIpv4InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime."
    ::= { gamIpStatisticsGlobalsIpv4 32 }

gamIpStatisticsGlobalsIpv4HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime."
    ::= { gamIpStatisticsGlobalsIpv4 33 }

gamIpStatisticsGlobalsIpv4InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime."
    ::= { gamIpStatisticsGlobalsIpv4 34 }

gamIpStatisticsGlobalsIpv4HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime."
    ::= { gamIpStatisticsGlobalsIpv4 35 }

gamIpStatisticsGlobalsIpv4OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime."
    ::= { gamIpStatisticsGlobalsIpv4 36 }

gamIpStatisticsGlobalsIpv4HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime."
    ::= { gamIpStatisticsGlobalsIpv4 37 }

gamIpStatisticsGlobalsIpv4OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime."
    ::= { gamIpStatisticsGlobalsIpv4 38 }

gamIpStatisticsGlobalsIpv4HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime."
    ::= { gamIpStatisticsGlobalsIpv4 39 }

gamIpStatisticsGlobalsIpv4InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime."
    ::= { gamIpStatisticsGlobalsIpv4 40 }

gamIpStatisticsGlobalsIpv4HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime."
    ::= { gamIpStatisticsGlobalsIpv4 41 }

gamIpStatisticsGlobalsIpv4OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime."
    ::= { gamIpStatisticsGlobalsIpv4 42 }

gamIpStatisticsGlobalsIpv4HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime."
    ::= { gamIpStatisticsGlobalsIpv4 43 }

gamIpStatisticsGlobalsIpv4DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value."
    ::= { gamIpStatisticsGlobalsIpv4 44 }

gamIpStatisticsGlobalsIpv4RefreshRate OBJECT-TYPE
    SYNTAX      Unsigned32
    MAX-ACCESS  read-only
    STATUS      current
    DESCRIPTION
        "The minimum reasonable polling interval for this entry. This object
         provides an indication of the minimum amount of time required to update
         the counters in this entry."
    ::= { gamIpStatisticsGlobalsIpv4 45 }

gamIpStatisticsGlobalsIpv6 OBJECT IDENTIFIER
    ::= { gamIpStatisticsGlobals 2 }

gamIpStatisticsGlobalsIpv6InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime."
    ::= { gamIpStatisticsGlobalsIpv6 1 }

gamIpStatisticsGlobalsIpv6HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime."
    ::= { gamIpStatisticsGlobalsIpv6 2 }

gamIpStatisticsGlobalsIpv6InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime."
    ::= { gamIpStatisticsGlobalsIpv6 3 }

gamIpStatisticsGlobalsIpv6HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime."
    ::= { gamIpStatisticsGlobalsIpv6 4 }

gamIpStatisticsGlobalsIpv6InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime."
    ::= { gamIpStatisticsGlobalsIpv6 5 }

gamIpStatisticsGlobalsIpv6InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime."
    ::= { gamIpStatisticsGlobalsIpv6 6 }

gamIpStatisticsGlobalsIpv6InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime."
    ::= { gamIpStatisticsGlobalsIpv6 7 }

gamIpStatisticsGlobalsIpv6InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { gamIpStatisticsGlobalsIpv6 8 }

gamIpStatisticsGlobalsIpv6InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime."
    ::= { gamIpStatisticsGlobalsIpv6 9 }

gamIpStatisticsGlobalsIpv6InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime."
    ::= { gamIpStatisticsGlobalsIpv6 10 }

gamIpStatisticsGlobalsIpv6HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime."
    ::= { gamIpStatisticsGlobalsIpv6 11 }

gamIpStatisticsGlobalsIpv6ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime."
    ::= { gamIpStatisticsGlobalsIpv6 12 }

gamIpStatisticsGlobalsIpv6ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { gamIpStatisticsGlobalsIpv6 13 }

gamIpStatisticsGlobalsIpv6ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime."
    ::= { gamIpStatisticsGlobalsIpv6 14 }

gamIpStatisticsGlobalsIpv6InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime."
    ::= { gamIpStatisticsGlobalsIpv6 15 }

gamIpStatisticsGlobalsIpv6InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime."
    ::= { gamIpStatisticsGlobalsIpv6 16 }

gamIpStatisticsGlobalsIpv6HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime."
    ::= { gamIpStatisticsGlobalsIpv6 17 }

gamIpStatisticsGlobalsIpv6OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime."
    ::= { gamIpStatisticsGlobalsIpv6 18 }

gamIpStatisticsGlobalsIpv6HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime."
    ::= { gamIpStatisticsGlobalsIpv6 19 }

gamIpStatisticsGlobalsIpv6OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime."
    ::= { gamIpStatisticsGlobalsIpv6 20 }

gamIpStatisticsGlobalsIpv6OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime."
    ::= { gamIpStatisticsGlobalsIpv6 21 }

gamIpStatisticsGlobalsIpv6HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime."
    ::= { gamIpStatisticsGlobalsIpv6 22 }

gamIpStatisticsGlobalsIpv6OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime."
    ::= { gamIpStatisticsGlobalsIpv6 23 }

gamIpStatisticsGlobalsIpv6OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime."
    ::= { gamIpStatisticsGlobalsIpv6 24 }

gamIpStatisticsGlobalsIpv6OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime."
    ::= { gamIpStatisticsGlobalsIpv6 25 }

gamIpStatisticsGlobalsIpv6OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime."
    ::= { gamIpStatisticsGlobalsIpv6 26 }

gamIpStatisticsGlobalsIpv6OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime."
    ::= { gamIpStatisticsGlobalsIpv6 27 }

gamIpStatisticsGlobalsIpv6OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime."
    ::= { gamIpStatisticsGlobalsIpv6 28 }

gamIpStatisticsGlobalsIpv6HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime."
    ::= { gamIpStatisticsGlobalsIpv6 29 }

gamIpStatisticsGlobalsIpv6OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime."
    ::= { gamIpStatisticsGlobalsIpv6 30 }

gamIpStatisticsGlobalsIpv6HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime."
    ::= { gamIpStatisticsGlobalsIpv6 31 }

gamIpStatisticsGlobalsIpv6InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime."
    ::= { gamIpStatisticsGlobalsIpv6 32 }

gamIpStatisticsGlobalsIpv6HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime."
    ::= { gamIpStatisticsGlobalsIpv6 33 }

gamIpStatisticsGlobalsIpv6InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime."
    ::= { gamIpStatisticsGlobalsIpv6 34 }

gamIpStatisticsGlobalsIpv6HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime."
    ::= { gamIpStatisticsGlobalsIpv6 35 }

gamIpStatisticsGlobalsIpv6OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime."
    ::= { gamIpStatisticsGlobalsIpv6 36 }

gamIpStatisticsGlobalsIpv6HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime."
    ::= { gamIpStatisticsGlobalsIpv6 37 }

gamIpStatisticsGlobalsIpv6OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime."
    ::= { gamIpStatisticsGlobalsIpv6 38 }

gamIpStatisticsGlobalsIpv6HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime."
    ::= { gamIpStatisticsGlobalsIpv6 39 }

gamIpStatisticsGlobalsIpv6InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime."
    ::= { gamIpStatisticsGlobalsIpv6 40 }

gamIpStatisticsGlobalsIpv6HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime."
    ::= { gamIpStatisticsGlobalsIpv6 41 }

gamIpStatisticsGlobalsIpv6OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime."
    ::= { gamIpStatisticsGlobalsIpv6 42 }

gamIpStatisticsGlobalsIpv6HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime."
    ::= { gamIpStatisticsGlobalsIpv6 43 }

gamIpStatisticsGlobalsIpv6DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value."
    ::= { gamIpStatisticsGlobalsIpv6 44 }

gamIpStatisticsGlobalsIpv6RefreshRate OBJECT-TYPE
    SYNTAX      Unsigned32
    MAX-ACCESS  read-only
    STATUS      current
    DESCRIPTION
        "The minimum reasonable polling interval for this entry. This object
         provides an indication of the minimum amount of time required to update
         the counters in this entry."
    ::= { gamIpStatisticsGlobalsIpv6 45 }

gamIpStatisticsInterfaces OBJECT IDENTIFIER
    ::= { gamIpStatistics 2 }

gamIpStatisticsInterfacesLinkTable OBJECT-TYPE
    SYNTAX      SEQUENCE OF GAMIpStatisticsInterfacesLinkEntry
    MAX-ACCESS  not-accessible
    STATUS      current
    DESCRIPTION
        "This table provides interface link statistics for a given IP interface."
    ::= { gamIpStatisticsInterfaces 1 }

gamIpStatisticsInterfacesLinkEntry OBJECT-TYPE
    SYNTAX      GAMIpStatisticsInterfacesLinkEntry
    MAX-ACCESS  not-accessible
    STATUS      current
    DESCRIPTION
        "Each entry in this table represents an IP interface."
    INDEX       { gamIpStatisticsInterfacesLinkIfIndex }
    ::= { gamIpStatisticsInterfacesLinkTable 1 }

GAMIpStatisticsInterfacesLinkEntry ::= SEQUENCE {
    gamIpStatisticsInterfacesLinkIfIndex        GAMInterfaceIndex,
    gamIpStatisticsInterfacesLinkInPackets      Counter64,
    gamIpStatisticsInterfacesLinkOutPackets     Counter64,
    gamIpStatisticsInterfacesLinkInBytes        Counter64,
    gamIpStatisticsInterfacesLinkOutBytes       Counter64,
    gamIpStatisticsInterfacesLinkInMulticasts   Counter64,
    gamIpStatisticsInterfacesLinkOutMulticasts  Counter64,
    gamIpStatisticsInterfacesLinkInBroadcasts   Counter64,
    gamIpStatisticsInterfacesLinkOutBroadcasts  Counter64
}

gamIpStatisticsInterfacesLinkIfIndex OBJECT-TYPE
    SYNTAX      GAMInterfaceIndex
    MAX-ACCESS  accessible-for-notify
    STATUS      current
    DESCRIPTION
        "Interface index number."
    ::= { gamIpStatisticsInterfacesLinkEntry 1 }

gamIpStatisticsInterfacesLinkInPackets OBJECT-TYPE
    SYNTAX      Counter64
    MAX-ACCESS  read-only
    STATUS      current
    DESCRIPTION
        "Number of packets delivered by MAC layer to IP layer."
    ::= { gamIpStatisticsInterfacesLinkEntry 2 }

gamIpStatisticsInterfacesLinkOutPackets OBJECT-TYPE
    SYNTAX      Counter64
    MAX-ACCESS  read-only
    STATUS      current
    DESCRIPTION
        "Number of packets IP protocols requested be transmitted, including
         those that were discarded or not sent."
    ::= { gamIpStatisticsInterfacesLinkEntry 3 }

gamIpStatisticsInterfacesLinkInBytes OBJECT-TYPE
    SYNTAX      Counter64
    MAX-ACCESS  read-only
    STATUS      current
    DESCRIPTION
        "Number of octets received on the interface, including framing
         characters."
    ::= { gamIpStatisticsInterfacesLinkEntry 4 }

gamIpStatisticsInterfacesLinkOutBytes OBJECT-TYPE
    SYNTAX      Counter64
    MAX-ACCESS  read-only
    STATUS      current
    DESCRIPTION
        "Number of octets transmitted out of the interface, including framing
         characters."
    ::= { gamIpStatisticsInterfacesLinkEntry 5 }

gamIpStatisticsInterfacesLinkInMulticasts OBJECT-TYPE
    SYNTAX      Counter64
    MAX-ACCESS  read-only
    STATUS      current
    DESCRIPTION
        "Number of packets delivered by MAC layer to IP layer that were
         addressed to a MAC multicast address.
         
         For a MAC layer protocol, this includes both Group and Functional
         addresses."
    ::= { gamIpStatisticsInterfacesLinkEntry 6 }

gamIpStatisticsInterfacesLinkOutMulticasts OBJECT-TYPE
    SYNTAX      Counter64
    MAX-ACCESS  read-only
    STATUS      current
    DESCRIPTION
        "Number of packets addressed to a multicast MAC address that IP
         protocols requested be transmitted, including those that were discarded
         or not sent.
         
         For a MAC layer protocol, this includes both Group and Functional
         addresses."
    ::= { gamIpStatisticsInterfacesLinkEntry 7 }

gamIpStatisticsInterfacesLinkInBroadcasts OBJECT-TYPE
    SYNTAX      Counter64
    MAX-ACCESS  read-only
    STATUS      current
    DESCRIPTION
        "Number of packets delivered by MAC layer to IP layer that were
         addressed to a MAC broadcast address."
    ::= { gamIpStatisticsInterfacesLinkEntry 8 }

gamIpStatisticsInterfacesLinkOutBroadcasts OBJECT-TYPE
    SYNTAX      Counter64
    MAX-ACCESS  read-only
    STATUS      current
    DESCRIPTION
        "Number of packets addressed to a broadcast MAC address that IP
         protocols requested be transmitted, including those that were discarded
         or not sent."
    ::= { gamIpStatisticsInterfacesLinkEntry 9 }

gamIpStatisticsInterfacesIpv4Table OBJECT-TYPE
    SYNTAX      SEQUENCE OF GAMIpStatisticsInterfacesIpv4Entry
    MAX-ACCESS  not-accessible
    STATUS      current
    DESCRIPTION
        "This table provides IPv4 related statitics for a given IP interface."
    ::= { gamIpStatisticsInterfaces 2 }

gamIpStatisticsInterfacesIpv4Entry OBJECT-TYPE
    SYNTAX      GAMIpStatisticsInterfacesIpv4Entry
    MAX-ACCESS  not-accessible
    STATUS      current
    DESCRIPTION
        "Each entry in this table represents an IP interface."
    INDEX       { gamIpStatisticsInterfacesIpv4IfIndex }
    ::= { gamIpStatisticsInterfacesIpv4Table 1 }

GAMIpStatisticsInterfacesIpv4Entry ::= SEQUENCE {
    gamIpStatisticsInterfacesIpv4IfIndex             GAMInterfaceIndex,
    gamIpStatisticsInterfacesIpv4InReceives          Unsigned32,
    gamIpStatisticsInterfacesIpv4HCInReceives        Counter64,
    gamIpStatisticsInterfacesIpv4InOctets            Unsigned32,
    gamIpStatisticsInterfacesIpv4HCInOctets          Counter64,
    gamIpStatisticsInterfacesIpv4InHdrErrors         Unsigned32,
    gamIpStatisticsInterfacesIpv4InNoRoutes          Unsigned32,
    gamIpStatisticsInterfacesIpv4InAddrErrors        Unsigned32,
    gamIpStatisticsInterfacesIpv4InUnknownProtos     Unsigned32,
    gamIpStatisticsInterfacesIpv4InTruncatedPkts     Unsigned32,
    gamIpStatisticsInterfacesIpv4InForwDatagrams     Unsigned32,
    gamIpStatisticsInterfacesIpv4HCInForwDatagrams   Counter64,
    gamIpStatisticsInterfacesIpv4ReasmReqds          Unsigned32,
    gamIpStatisticsInterfacesIpv4ReasmOKs            Unsigned32,
    gamIpStatisticsInterfacesIpv4ReasmFails          Unsigned32,
    gamIpStatisticsInterfacesIpv4InDiscards          Unsigned32,
    gamIpStatisticsInterfacesIpv4InDelivers          Unsigned32,
    gamIpStatisticsInterfacesIpv4HCInDelivers        Counter64,
    gamIpStatisticsInterfacesIpv4OutRequests         Unsigned32,
    gamIpStatisticsInterfacesIpv4HCOutRequests       Counter64,
    gamIpStatisticsInterfacesIpv4OutNoRoutes         Unsigned32,
    gamIpStatisticsInterfacesIpv4OutForwDatagrams    Unsigned32,
    gamIpStatisticsInterfacesIpv4HCOutForwDatagrams  Counter64,
    gamIpStatisticsInterfacesIpv4OutDiscards         Unsigned32,
    gamIpStatisticsInterfacesIpv4OutFragReqds        Unsigned32,
    gamIpStatisticsInterfacesIpv4OutFragOKs          Unsigned32,
    gamIpStatisticsInterfacesIpv4OutFragFails        Unsigned32,
    gamIpStatisticsInterfacesIpv4OutFragCreates      Unsigned32,
    gamIpStatisticsInterfacesIpv4OutTransmits        Unsigned32,
    gamIpStatisticsInterfacesIpv4HCOutTransmits      Counter64,
    gamIpStatisticsInterfacesIpv4OutOctets           Unsigned32,
    gamIpStatisticsInterfacesIpv4HCOutOctets         Counter64,
    gamIpStatisticsInterfacesIpv4InMcastPkts         Unsigned32,
    gamIpStatisticsInterfacesIpv4HCInMcastPkts       Counter64,
    gamIpStatisticsInterfacesIpv4InMcastOctets       Unsigned32,
    gamIpStatisticsInterfacesIpv4HCInMcastOctets     Counter64,
    gamIpStatisticsInterfacesIpv4OutMcastPkts        Unsigned32,
    gamIpStatisticsInterfacesIpv4HCOutMcastPkts      Counter64,
    gamIpStatisticsInterfacesIpv4OutMcastOctets      Unsigned32,
    gamIpStatisticsInterfacesIpv4HCOutMcastOctets    Counter64,
    gamIpStatisticsInterfacesIpv4InBcastPkts         Unsigned32,
    gamIpStatisticsInterfacesIpv4HCInBcastPkts       Counter64,
    gamIpStatisticsInterfacesIpv4OutBcastPkts        Unsigned32,
    gamIpStatisticsInterfacesIpv4HCOutBcastPkts      Counter64,
    gamIpStatisticsInterfacesIpv4DiscontinuityTime   Counter64,
    gamIpStatisticsInterfacesIpv4RefreshRate         Unsigned32
}

gamIpStatisticsInterfacesIpv4IfIndex OBJECT-TYPE
    SYNTAX      GAMInterfaceIndex
    MAX-ACCESS  accessible-for-notify
    STATUS      current
    DESCRIPTION
        "Interface index number.
         
         This object is only available if the capability object
         'gamIpCapabilitiesHasPerInterfaceIpv4Statistics' is True."
    ::= { gamIpStatisticsInterfacesIpv4Entry 1 }

gamIpStatisticsInterfacesIpv4InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 2 }

gamIpStatisticsInterfacesIpv4HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 3 }

gamIpStatisticsInterfacesIpv4InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 4 }

gamIpStatisticsInterfacesIpv4HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 5 }

gamIpStatisticsInterfacesIpv4InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 6 }

gamIpStatisticsInterfacesIpv4InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 7 }

gamIpStatisticsInterfacesIpv4InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 8 }

gamIpStatisticsInterfacesIpv4InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 9 }

gamIpStatisticsInterfacesIpv4InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 10 }

gamIpStatisticsInterfacesIpv4InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 11 }

gamIpStatisticsInterfacesIpv4HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 12 }

gamIpStatisticsInterfacesIpv4ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 13 }

gamIpStatisticsInterfacesIpv4ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 14 }

gamIpStatisticsInterfacesIpv4ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 15 }

gamIpStatisticsInterfacesIpv4InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 16 }

gamIpStatisticsInterfacesIpv4InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 17 }

gamIpStatisticsInterfacesIpv4HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 18 }

gamIpStatisticsInterfacesIpv4OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 19 }

gamIpStatisticsInterfacesIpv4HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 20 }

gamIpStatisticsInterfacesIpv4OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 21 }

gamIpStatisticsInterfacesIpv4OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 22 }

gamIpStatisticsInterfacesIpv4HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 23 }

gamIpStatisticsInterfacesIpv4OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 24 }

gamIpStatisticsInterfacesIpv4OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 25 }

gamIpStatisticsInterfacesIpv4OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 26 }

gamIpStatisticsInterfacesIpv4OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 27 }

gamIpStatisticsInterfacesIpv4OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 28 }

gamIpStatisticsInterfacesIpv4OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 29 }

gamIpStatisticsInterfacesIpv4HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 30 }

gamIpStatisticsInterfacesIpv4OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 31 }

gamIpStatisticsInterfacesIpv4HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 32 }

gamIpStatisticsInterfacesIpv4InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 33 }

gamIpStatisticsInterfacesIpv4HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 34 }

gamIpStatisticsInterfacesIpv4InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 35 }

gamIpStatisticsInterfacesIpv4HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 36 }

gamIpStatisticsInterfacesIpv4OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 37 }

gamIpStatisticsInterfacesIpv4HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 38 }

gamIpStatisticsInterfacesIpv4OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 39 }

gamIpStatisticsInterfacesIpv4HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 40 }

gamIpStatisticsInterfacesIpv4InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 41 }

gamIpStatisticsInterfacesIpv4HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 42 }

gamIpStatisticsInterfacesIpv4OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 43 }

gamIpStatisticsInterfacesIpv4HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime.
         
         This object is only available if the capability object
         'gamIpCapabilitiesHasPerInterfaceIpv4Statistics' is True."
    ::= { gamIpStatisticsInterfacesIpv4Entry 44 }

gamIpStatisticsInterfacesIpv4DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value.
         
         This object is only available if the capability object
         'gamIpCapabilitiesHasPerInterfaceIpv4Statistics' is True."
    ::= { gamIpStatisticsInterfacesIpv4Entry 45 }

gamIpStatisticsInterfacesIpv4RefreshRate OBJECT-TYPE
    SYNTAX      Unsigned32
    MAX-ACCESS  read-only
    STATUS      current
    DESCRIPTION
        "The minimum reasonable polling interval for this entry. This object
         provides an indication of the minimum amount of time required to update
         the counters in this entry.
         
         This object is only available if the capability object
         'gamIpCapabilitiesHasPerInterfaceIpv4Statistics' is True."
    ::= { gamIpStatisticsInterfacesIpv4Entry 46 }

gamIpStatisticsInterfacesIpv6Table OBJECT-TYPE
    SYNTAX      SEQUENCE OF GAMIpStatisticsInterfacesIpv6Entry
    MAX-ACCESS  not-accessible
    STATUS      current
    DESCRIPTION
        "This table provides IPv6 related statitics for a given IP interface."
    ::= { gamIpStatisticsInterfaces 3 }

gamIpStatisticsInterfacesIpv6Entry OBJECT-TYPE
    SYNTAX      GAMIpStatisticsInterfacesIpv6Entry
    MAX-ACCESS  not-accessible
    STATUS      current
    DESCRIPTION
        "Each entry in this table represents an IP interface."
    INDEX       { gamIpStatisticsInterfacesIpv6IfIndex }
    ::= { gamIpStatisticsInterfacesIpv6Table 1 }

GAMIpStatisticsInterfacesIpv6Entry ::= SEQUENCE {
    gamIpStatisticsInterfacesIpv6IfIndex             GAMInterfaceIndex,
    gamIpStatisticsInterfacesIpv6InReceives          Unsigned32,
    gamIpStatisticsInterfacesIpv6HCInReceives        Counter64,
    gamIpStatisticsInterfacesIpv6InOctets            Unsigned32,
    gamIpStatisticsInterfacesIpv6HCInOctets          Counter64,
    gamIpStatisticsInterfacesIpv6InHdrErrors         Unsigned32,
    gamIpStatisticsInterfacesIpv6InNoRoutes          Unsigned32,
    gamIpStatisticsInterfacesIpv6InAddrErrors        Unsigned32,
    gamIpStatisticsInterfacesIpv6InUnknownProtos     Unsigned32,
    gamIpStatisticsInterfacesIpv6InTruncatedPkts     Unsigned32,
    gamIpStatisticsInterfacesIpv6InForwDatagrams     Unsigned32,
    gamIpStatisticsInterfacesIpv6HCInForwDatagrams   Counter64,
    gamIpStatisticsInterfacesIpv6ReasmReqds          Unsigned32,
    gamIpStatisticsInterfacesIpv6ReasmOKs            Unsigned32,
    gamIpStatisticsInterfacesIpv6ReasmFails          Unsigned32,
    gamIpStatisticsInterfacesIpv6InDiscards          Unsigned32,
    gamIpStatisticsInterfacesIpv6InDelivers          Unsigned32,
    gamIpStatisticsInterfacesIpv6HCInDelivers        Counter64,
    gamIpStatisticsInterfacesIpv6OutRequests         Unsigned32,
    gamIpStatisticsInterfacesIpv6HCOutRequests       Counter64,
    gamIpStatisticsInterfacesIpv6OutNoRoutes         Unsigned32,
    gamIpStatisticsInterfacesIpv6OutForwDatagrams    Unsigned32,
    gamIpStatisticsInterfacesIpv6HCOutForwDatagrams  Counter64,
    gamIpStatisticsInterfacesIpv6OutDiscards         Unsigned32,
    gamIpStatisticsInterfacesIpv6OutFragReqds        Unsigned32,
    gamIpStatisticsInterfacesIpv6OutFragOKs          Unsigned32,
    gamIpStatisticsInterfacesIpv6OutFragFails        Unsigned32,
    gamIpStatisticsInterfacesIpv6OutFragCreates      Unsigned32,
    gamIpStatisticsInterfacesIpv6OutTransmits        Unsigned32,
    gamIpStatisticsInterfacesIpv6HCOutTransmits      Counter64,
    gamIpStatisticsInterfacesIpv6OutOctets           Unsigned32,
    gamIpStatisticsInterfacesIpv6HCOutOctets         Counter64,
    gamIpStatisticsInterfacesIpv6InMcastPkts         Unsigned32,
    gamIpStatisticsInterfacesIpv6HCInMcastPkts       Counter64,
    gamIpStatisticsInterfacesIpv6InMcastOctets       Unsigned32,
    gamIpStatisticsInterfacesIpv6HCInMcastOctets     Counter64,
    gamIpStatisticsInterfacesIpv6OutMcastPkts        Unsigned32,
    gamIpStatisticsInterfacesIpv6HCOutMcastPkts      Counter64,
    gamIpStatisticsInterfacesIpv6OutMcastOctets      Unsigned32,
    gamIpStatisticsInterfacesIpv6HCOutMcastOctets    Counter64,
    gamIpStatisticsInterfacesIpv6InBcastPkts         Unsigned32,
    gamIpStatisticsInterfacesIpv6HCInBcastPkts       Counter64,
    gamIpStatisticsInterfacesIpv6OutBcastPkts        Unsigned32,
    gamIpStatisticsInterfacesIpv6HCOutBcastPkts      Counter64,
    gamIpStatisticsInterfacesIpv6DiscontinuityTime   Counter64,
    gamIpStatisticsInterfacesIpv6RefreshRate         Unsigned32
}

gamIpStatisticsInterfacesIpv6IfIndex OBJECT-TYPE
    SYNTAX      GAMInterfaceIndex
    MAX-ACCESS  accessible-for-notify
    STATUS      current
    DESCRIPTION
        "Interface index number.
         
         This object is only available if the capability object
         'gamIpCapabilitiesHasPerInterfaceIpv6Statistics' is True."
    ::= { gamIpStatisticsInterfacesIpv6Entry 1 }

gamIpStatisticsInterfacesIpv6InReceives OBJECT-TYPE
    SYNTAX      Unsigned32
    MAX-ACCESS  read-only
    STATUS      current
    DESCRIPTION
        "Number of input IP datagrams received, including those received in
         error.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 2 }

gamIpStatisticsInterfacesIpv6HCInReceives OBJECT-TYPE
    SYNTAX      Counter64
    MAX-ACCESS  read-only
    STATUS      current
    DESCRIPTION
        "Number of input IP datagrams received, including those received in
         error. This object counts the same datagrams as InReceives, but allows
         for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 3 }

gamIpStatisticsInterfacesIpv6InOctets OBJECT-TYPE
    SYNTAX      Unsigned32
    MAX-ACCESS  read-only
    STATUS      current
    DESCRIPTION
        "Number of octets received in input IP datagrams, including those
         received in error. Octets from datagrams counted in InReceives must be
         counted here.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 4 }

gamIpStatisticsInterfacesIpv6HCInOctets OBJECT-TYPE
    SYNTAX      Counter64
    MAX-ACCESS  read-only
    STATUS      current
    DESCRIPTION
        "Number of octets received in input IP datagrams, including those
         received in error. This object counts the same octets as InOctets, but
         allows for a larger value.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 5 }

gamIpStatisticsInterfacesIpv6InHdrErrors OBJECT-TYPE
    SYNTAX      Unsigned32
    MAX-ACCESS  read-only
    STATUS      current
    DESCRIPTION
        "Number of input IP datagrams discarded due to errors in their IP
         headers, including version number mismatch, other format errors, hop
         count exceeded, and errors discovered in processing their IP options.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 6 }

gamIpStatisticsInterfacesIpv6InNoRoutes OBJECT-TYPE
    SYNTAX      Unsigned32
    MAX-ACCESS  read-only
    STATUS      current
    DESCRIPTION
        "Number of input IP datagrams discarded because no route could be found
         to transmit them to their destination.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 7 }

gamIpStatisticsInterfacesIpv6InAddrErrors OBJECT-TYPE
    SYNTAX      Unsigned32
    MAX-ACCESS  read-only
    STATUS      current
    DESCRIPTION
        "Number of input IP datagrams discarded because the IP address in their
         IP header's destination field was not a valid address to be received at
         this entity. This count includes invalid addresses (e.g., ::0). For
         entities that are not IP routers and therefore do not forward
         datagrams, this counter includes datagrams discarded because the
         destination address was not a local address.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 8 }

gamIpStatisticsInterfacesIpv6InUnknownProtos OBJECT-TYPE
    SYNTAX      Unsigned32
    MAX-ACCESS  read-only
    STATUS      current
    DESCRIPTION
        "Number of locally-addressed IP datagrams received successfully but
         discarded because of an unknown or unsupported protocol.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 9 }

gamIpStatisticsInterfacesIpv6InTruncatedPkts OBJECT-TYPE
    SYNTAX      Unsigned32
    MAX-ACCESS  read-only
    STATUS      current
    DESCRIPTION
        "Number of input IP datagrams discarded because the datagram frame
         didn't carry enough data.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 10 }

gamIpStatisticsInterfacesIpv6InForwDatagrams OBJECT-TYPE
    SYNTAX      Unsigned32
    MAX-ACCESS  read-only
    STATUS      current
    DESCRIPTION
        "Number of input datagrams for which this entity was not their final IP
         destination and for which this entity attempted to find a route to
         forward them to their final destination.
         
         When tracking interface statistics, the counter of the incoming
         interface is incremented for each datagram.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 11 }

gamIpStatisticsInterfacesIpv6HCInForwDatagrams OBJECT-TYPE
    SYNTAX      Counter64
    MAX-ACCESS  read-only
    STATUS      current
    DESCRIPTION
        "Number of input datagrams for which this entity was not their final IP
         destination and for which this entity attempted to find a route to
         forward them to their final destination. This object counts the same
         packets as InForwDatagrams, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 12 }

gamIpStatisticsInterfacesIpv6ReasmReqds OBJECT-TYPE
    SYNTAX      Unsigned32
    MAX-ACCESS  read-only
    STATUS      current
    DESCRIPTION
        "Number of IP fragments received that needed to be reassembled at this
         interface.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 13 }

gamIpStatisticsInterfacesIpv6ReasmOKs OBJECT-TYPE
    SYNTAX      Unsigned32
    MAX-ACCESS  read-only
    STATUS      current
    DESCRIPTION
        "Number of IP datagrams successfully reassembled.
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 14 }

gamIpStatisticsInterfacesIpv6ReasmFails OBJECT-TYPE
    SYNTAX      Unsigned32
    MAX-ACCESS  read-only
    STATUS      current
    DESCRIPTION
        "Number of failures detected by the IP re-assembly algorithm.
         
         Note: this is not necessarily a count of discarded IP fragments because
         some algorithms (notably the algorithm in RFC 815) can lose track of
         the number of fragments by combining them as they are received.
         
         When tracking interface statistics, the counter of the interface to
         which these fragments were addressed is incremented. This interface
         might not be the same as the input interface for some of the fragments.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 15 }

gamIpStatisticsInterfacesIpv6InDiscards OBJECT-TYPE
    SYNTAX      Unsigned32
    MAX-ACCESS  read-only
    STATUS      current
    DESCRIPTION
        "Number of input IP datagrams for which no problems were encountered to
         prevent their continued processing, but were discarded.
         
         Note: this counter does not include any datagrams discarded while
         awaiting re-assembly.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 16 }

gamIpStatisticsInterfacesIpv6InDelivers OBJECT-TYPE
    SYNTAX      Unsigned32
    MAX-ACCESS  read-only
    STATUS      current
    DESCRIPTION
        "Number of datagrams successfully delivered to IP user-protocols
         (including ICMP).
         
         When tracking interface statistics, the counter of the interface to
         which these datagrams were addressed is incremented. This interface
         might not be the same as the input interface for some of the datagrams.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 17 }

gamIpStatisticsInterfacesIpv6HCInDelivers OBJECT-TYPE
    SYNTAX      Counter64
    MAX-ACCESS  read-only
    STATUS      current
    DESCRIPTION
        "Number of datagrams successfully delivered to IP user-protocols
         (including ICMP). This object counts the same packets as
         ipSystemStatsInDelivers, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 18 }

gamIpStatisticsInterfacesIpv6OutRequests OBJECT-TYPE
    SYNTAX      Unsigned32
    MAX-ACCESS  read-only
    STATUS      current
    DESCRIPTION
        "Number of IP datagrams that local IP user-protocols (including ICMP)
         supplied to IP in requests for transmission.
         
         Note: this counter does not include any datagrams counted in
         OutForwDatagrams.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 19 }

gamIpStatisticsInterfacesIpv6HCOutRequests OBJECT-TYPE
    SYNTAX      Counter64
    MAX-ACCESS  read-only
    STATUS      current
    DESCRIPTION
        "Number of IP datagrams that local IP user-protocols (including ICMP)
         supplied to IP in requests for transmission. This object counts the
         same packets as OutRequests, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 20 }

gamIpStatisticsInterfacesIpv6OutNoRoutes OBJECT-TYPE
    SYNTAX      Unsigned32
    MAX-ACCESS  read-only
    STATUS      current
    DESCRIPTION
        "Number of locally generated IP datagrams discarded because no route
         could be found to transmit them to their destination.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 21 }

gamIpStatisticsInterfacesIpv6OutForwDatagrams OBJECT-TYPE
    SYNTAX      Unsigned32
    MAX-ACCESS  read-only
    STATUS      current
    DESCRIPTION
        "Number of datagrams for which this entity was not their final IP
         destination and for which it was successful in finding a path to their
         final destination.
         
         When tracking interface statistics, the counter of the outgoing
         interface is incremented for a successfully forwarded datagram.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 22 }

gamIpStatisticsInterfacesIpv6HCOutForwDatagrams OBJECT-TYPE
    SYNTAX      Counter64
    MAX-ACCESS  read-only
    STATUS      current
    DESCRIPTION
        "Number of datagrams for which this entity was not their final IP
         destination and for which it was successful in finding a path to their
         final destination. This object counts the same packets as
         OutForwDatagrams, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 23 }

gamIpStatisticsInterfacesIpv6OutDiscards OBJECT-TYPE
    SYNTAX      Unsigned32
    MAX-ACCESS  read-only
    STATUS      current
    DESCRIPTION
        "Number of output IP datagrams for which no problem was encountered to
         prevent their transmission to their destination, but were discarded.
         
         Note: this counter includes datagrams counted in OutForwDatagrams if
         any such datagrams met this (discretionary) discard criterion.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 24 }

gamIpStatisticsInterfacesIpv6OutFragReqds OBJECT-TYPE
    SYNTAX      Unsigned32
    MAX-ACCESS  read-only
    STATUS      current
    DESCRIPTION
        "Number of IP datagrams that require fragmentation in order to be
         transmitted.
         
         When tracking interface statistics, the counter of the outgoing
         interface is incremented for a successfully fragmented datagram.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 25 }

gamIpStatisticsInterfacesIpv6OutFragOKs OBJECT-TYPE
    SYNTAX      Unsigned32
    MAX-ACCESS  read-only
    STATUS      current
    DESCRIPTION
        "Number of IP datagrams that have been successfully fragmented.
         
         When tracking interface statistics, the counter of the outgoing
         interface is incremented for a successfully fragmented datagram.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 26 }

gamIpStatisticsInterfacesIpv6OutFragFails OBJECT-TYPE
    SYNTAX      Unsigned32
    MAX-ACCESS  read-only
    STATUS      current
    DESCRIPTION
        "Number of IP datagrams that have been discarded because they needed to
         be fragmented but could not be. This includes IPv4 packets that have
         the DF bit set and IPv6 packets that are being forwarded and exceed the
         outgoing link MTU.
         
         When tracking interface statistics, the counter of the outgoing
         interface is incremented for an unsuccessfully fragmented datagram.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 27 }

gamIpStatisticsInterfacesIpv6OutFragCreates OBJECT-TYPE
    SYNTAX      Unsigned32
    MAX-ACCESS  read-only
    STATUS      current
    DESCRIPTION
        "Number of output datagram fragments that have been generated as a
         result of IP fragmentation.
         
         When tracking interface statistics, the counter of the outgoing
         interface is incremented for a successfully fragmented datagram.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 28 }

gamIpStatisticsInterfacesIpv6OutTransmits OBJECT-TYPE
    SYNTAX      Unsigned32
    MAX-ACCESS  read-only
    STATUS      current
    DESCRIPTION
        "Number of IP datagrams that this entity supplied to the lower layers
         for transmission. This includes datagrams generated locally and those
         forwarded by this entity.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 29 }

gamIpStatisticsInterfacesIpv6HCOutTransmits OBJECT-TYPE
    SYNTAX      Counter64
    MAX-ACCESS  read-only
    STATUS      current
    DESCRIPTION
        "Number of IP datagrams that this entity supplied to the lower layers
         for transmission. This object counts the same datagrams as
         OutTransmits, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 30 }

gamIpStatisticsInterfacesIpv6OutOctets OBJECT-TYPE
    SYNTAX      Unsigned32
    MAX-ACCESS  read-only
    STATUS      current
    DESCRIPTION
        "Number of octets in IP datagrams delivered to the lower layers for
         transmission. Octets from datagrams counted in OutTransmits must be
         counted here.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 31 }

gamIpStatisticsInterfacesIpv6HCOutOctets OBJECT-TYPE
    SYNTAX      Counter64
    MAX-ACCESS  read-only
    STATUS      current
    DESCRIPTION
        "Number of octets in IP datagrams delivered to the lower layers for
         transmission. This objects counts the same octets as OutOctets, but
         allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 32 }

gamIpStatisticsInterfacesIpv6InMcastPkts OBJECT-TYPE
    SYNTAX      Unsigned32
    MAX-ACCESS  read-only
    STATUS      current
    DESCRIPTION
        "Number of IP multicast datagrams received.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 33 }

gamIpStatisticsInterfacesIpv6HCInMcastPkts OBJECT-TYPE
    SYNTAX      Counter64
    MAX-ACCESS  read-only
    STATUS      current
    DESCRIPTION
        "Number of IP multicast datagrams received. This object counts the same
         datagrams as InMcastPkts but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 34 }

gamIpStatisticsInterfacesIpv6InMcastOctets OBJECT-TYPE
    SYNTAX      Unsigned32
    MAX-ACCESS  read-only
    STATUS      current
    DESCRIPTION
        "Number of octets received in IP multicast datagrams. Octets from
         datagrams counted in InMcastPkts MUST be counted here.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 35 }

gamIpStatisticsInterfacesIpv6HCInMcastOctets OBJECT-TYPE
    SYNTAX      Counter64
    MAX-ACCESS  read-only
    STATUS      current
    DESCRIPTION
        "Number of octets received in IP multicast datagrams. This object counts
         the same octets as InMcastOctets, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 36 }

gamIpStatisticsInterfacesIpv6OutMcastPkts OBJECT-TYPE
    SYNTAX      Unsigned32
    MAX-ACCESS  read-only
    STATUS      current
    DESCRIPTION
        "Number of IP multicast datagrams transmitted.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 37 }

gamIpStatisticsInterfacesIpv6HCOutMcastPkts OBJECT-TYPE
    SYNTAX      Counter64
    MAX-ACCESS  read-only
    STATUS      current
    DESCRIPTION
        "Number of IP multicast datagrams transmitted. This object counts the
         same datagrams as OutMcastPkts, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 38 }

gamIpStatisticsInterfacesIpv6OutMcastOctets OBJECT-TYPE
    SYNTAX      Unsigned32
    MAX-ACCESS  read-only
    STATUS      current
    DESCRIPTION
        "Number of octets transmitted in IP multicast datagrams. Octets from
         datagrams counted in OutMcastPkts must be counted here.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 39 }

gamIpStatisticsInterfacesIpv6HCOutMcastOctets OBJECT-TYPE
    SYNTAX      Counter64
    MAX-ACCESS  read-only
    STATUS      current
    DESCRIPTION
        "Number of octets transmitted in IP multicast datagrams. This object
         counts the same octets as OutMcastOctets, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 40 }

gamIpStatisticsInterfacesIpv6InBcastPkts OBJECT-TYPE
    SYNTAX      Unsigned32
    MAX-ACCESS  read-only
    STATUS      current
    DESCRIPTION
        "Number of IP broadcast datagrams received.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 41 }

gamIpStatisticsInterfacesIpv6HCInBcastPkts OBJECT-TYPE
    SYNTAX      Counter64
    MAX-ACCESS  read-only
    STATUS      current
    DESCRIPTION
        "Number of IP broadcast datagrams received. This object counts the same
         datagrams as InBcastPkts but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 42 }

gamIpStatisticsInterfacesIpv6OutBcastPkts OBJECT-TYPE
    SYNTAX      Unsigned32
    MAX-ACCESS  read-only
    STATUS      current
    DESCRIPTION
        "Number of IP broadcast datagrams transmitted.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 43 }

gamIpStatisticsInterfacesIpv6HCOutBcastPkts OBJECT-TYPE
    SYNTAX      Counter64
    MAX-ACCESS  read-only
    STATUS      current
    DESCRIPTION
        "Number of IP broadcast datagrams transmitted. This object counts the
         same datagrams as OutBcastPkts, but allows for larger values.
         
         Discontinuities in the value of this counter may occur at
         re-initialization of the system, and at other times as indicated by the
         value of DiscontinuityTime.
         
         This object is only available if the capability object
         'gamIpCapabilitiesHasPerInterfaceIpv6Statistics' is True."
    ::= { gamIpStatisticsInterfacesIpv6Entry 44 }

gamIpStatisticsInterfacesIpv6DiscontinuityTime OBJECT-TYPE
    SYNTAX      Counter64
    MAX-ACCESS  read-only
    STATUS      current
    DESCRIPTION
        "Value of sysUpTime on the most recent occasion when any one or more of
         this entry's counters suffered a discontinuity.
         
         If no such discontinuities have occurred since the last
         re-initialization of the IP stack, then this object contains a zero
         value.
         
         This object is only available if the capability object
         'gamIpCapabilitiesHasPerInterfaceIpv6Statistics' is True."
    ::= { gamIpStatisticsInterfacesIpv6Entry 45 }

gamIpStatisticsInterfacesIpv6RefreshRate OBJECT-TYPE
    SYNTAX      Unsigned32
    MAX-ACCESS  read-only
    STATUS      current
    DESCRIPTION
        "The minimum reasonable polling interval for this entry. This object
         provides an indication of the minimum amount of time required to update
         the counters in this entry.
         
         This object is only available if the capability object
         'gamIpCapabilitiesHasPerInterfaceIpv6Statistics' is True."
    ::= { gamIpStatisticsInterfacesIpv6Entry 46 }

gamIpTrap OBJECT IDENTIFIER
    ::= { gamIpMibObjects 6 }

gamIpTrapInterfacesLinkAdd NOTIFICATION-TYPE
    OBJECTS     { gamIpStatusInterfacesLinkIfIndex,
                  gamIpStatusInterfacesLinkOsInterfaceIndex,
                  gamIpStatusInterfacesLinkMtu,
                  gamIpStatusInterfacesLinkMacAddress,
                  gamIpStatusInterfacesLinkUp,
                  gamIpStatusInterfacesLinkBroadcast,
                  gamIpStatusInterfacesLinkLoopback,
                  gamIpStatusInterfacesLinkRunning,
                  gamIpStatusInterfacesLinkNoarp,
                  gamIpStatusInterfacesLinkPromisc,
                  gamIpStatusInterfacesLinkMulticast }
    STATUS      current
    DESCRIPTION
        "This trap signals that a row has been added. The index(es) and value(s)
         of the row is included in the trap."

    ::= { gamIpTrap 1 }

gamIpTrapInterfacesLinkMod NOTIFICATION-TYPE
    OBJECTS     { gamIpStatusInterfacesLinkIfIndex,
                  gamIpStatusInterfacesLinkOsInterfaceIndex,
                  gamIpStatusInterfacesLinkMtu,
                  gamIpStatusInterfacesLinkMacAddress,
                  gamIpStatusInterfacesLinkUp,
                  gamIpStatusInterfacesLinkBroadcast,
                  gamIpStatusInterfacesLinkLoopback,
                  gamIpStatusInterfacesLinkRunning,
                  gamIpStatusInterfacesLinkNoarp,
                  gamIpStatusInterfacesLinkPromisc,
                  gamIpStatusInterfacesLinkMulticast }
    STATUS      current
    DESCRIPTION
        "This trap signals that one or more of the objects included in the trap
          has been updated."

    ::= { gamIpTrap 2 }

gamIpTrapInterfacesLinkDel NOTIFICATION-TYPE
    OBJECTS     { gamIpStatusInterfacesLinkIfIndex }
    STATUS      current
    DESCRIPTION
        "This trap signals that a row has been deleted. The index(es) of the
         row is included in the trap."

    ::= { gamIpTrap 3 }

gamIpMibConformance OBJECT IDENTIFIER
    ::= { gamIpMib 2 }

gamIpMibCompliances OBJECT IDENTIFIER
    ::= { gamIpMibConformance 1 }

gamIpMibGroups OBJECT IDENTIFIER
    ::= { gamIpMibConformance 2 }

gamIpCapabilitiesInfoGroup OBJECT-GROUP
    OBJECTS     { gamIpCapabilitiesHasIpv4HostCapabilities,
                  gamIpCapabilitiesHasIpv6HostCapabilities,
                  gamIpCapabilitiesHasIpv4UnicastRoutingCapabilities,
                  gamIpCapabilitiesHasIpv4UnicastHwRoutingCapabilities,
                  gamIpCapabilitiesHasIpv6UnicastRoutingCapabilities,
                  gamIpCapabilitiesHasIpv6UnicastHwRoutingCapabilities,
                  gamIpCapabilitiesMaxNumberOfIpInterfaces,
                  gamIpCapabilitiesMaxNumberOfStaticRoutes,
                  gamIpCapabilitiesNumberOfLpmHardwareEntries,
                  gamIpCapabilitiesHasPerInterfaceIpv4Statistics,
                  gamIpCapabilitiesHasPerInterfaceIpv6Statistics }
    STATUS      current
    DESCRIPTION
        "A collection of objects."
    ::= { gamIpMibGroups 1 }

gamIpConfigGlobalsMainInfoGroup OBJECT-GROUP
    OBJECTS     { gamIpConfigGlobalsMainEnableRouting }
    STATUS      current
    DESCRIPTION
        "A collection of objects."
    ::= { gamIpMibGroups 2 }

gamIpConfigInterfacesTableInfoGroup OBJECT-GROUP
    OBJECTS     { gamIpConfigInterfacesIfIndex,
                  gamIpConfigInterfacesAction }
    STATUS      current
    DESCRIPTION
        "A collection of objects."
    ::= { gamIpMibGroups 3 }

gamIpConfigInterfacesTableRowEditorInfoGroup OBJECT-GROUP
    OBJECTS     { gamIpConfigInterfacesTableRowEditorIfIndex,
                  gamIpConfigInterfacesTableRowEditorAction }
    STATUS      current
    DESCRIPTION
        "A collection of objects."
    ::= { gamIpMibGroups 4 }

gamIpConfigInterfacesIpv4TableInfoGroup OBJECT-GROUP
    OBJECTS     { gamIpConfigInterfacesIpv4IfIndex,
                  gamIpConfigInterfacesIpv4Active,
                  gamIpConfigInterfacesIpv4EnableDhcpClient,
                  gamIpConfigInterfacesIpv4Ipv4Address,
                  gamIpConfigInterfacesIpv4PrefixSize,
                  gamIpConfigInterfacesIpv4DhcpClientFallbackTimeout,
                  gamIpConfigInterfacesIpv4DhcpClientHostname,
                  gamIpConfigInterfacesIpv4DhcpClientIdType,
                  gamIpConfigInterfacesIpv4DhcpClientIdIfMac,
                  gamIpConfigInterfacesIpv4DhcpClientIdAscii,
                  gamIpConfigInterfacesIpv4DhcpClientIdHex }
    STATUS      current
    DESCRIPTION
        "A collection of objects."
    ::= { gamIpMibGroups 5 }

gamIpConfigInterfacesIpv6TableInfoGroup OBJECT-GROUP
    OBJECTS     { gamIpConfigInterfacesIpv6IfIndex,
                  gamIpConfigInterfacesIpv6Active,
                  gamIpConfigInterfacesIpv6Ipv6Address,
                  gamIpConfigInterfacesIpv6PrefixSize }
    STATUS      current
    DESCRIPTION
        "A collection of objects."
    ::= { gamIpMibGroups 6 }

gamIpConfigRoutesIpv4TableInfoGroup OBJECT-GROUP
    OBJECTS     { gamIpConfigRoutesIpv4NetworkAddress,
                  gamIpConfigRoutesIpv4NetworkPrefixSize,
                  gamIpConfigRoutesIpv4NextHop,
                  gamIpConfigRoutesIpv4Action }
    STATUS      current
    DESCRIPTION
        "A collection of objects."
    ::= { gamIpMibGroups 7 }

gamIpConfigRoutesIpv4RowEditorInfoGroup OBJECT-GROUP
    OBJECTS     { gamIpConfigRoutesIpv4RowEditorNetworkAddress,
                  gamIpConfigRoutesIpv4RowEditorNetworkPrefixSize,
                  gamIpConfigRoutesIpv4RowEditorNextHop,
                  gamIpConfigRoutesIpv4RowEditorAction }
    STATUS      current
    DESCRIPTION
        "A collection of objects."
    ::= { gamIpMibGroups 8 }

gamIpConfigRoutesIpv6TableInfoGroup OBJECT-GROUP
    OBJECTS     { gamIpConfigRoutesIpv6NetworkAddress,
                  gamIpConfigRoutesIpv6NetworkPrefixSize,
                  gamIpConfigRoutesIpv6NextHop,
                  gamIpConfigRoutesIpv6NextHopInterface,
                  gamIpConfigRoutesIpv6Action }
    STATUS      current
    DESCRIPTION
        "A collection of objects."
    ::= { gamIpMibGroups 9 }

gamIpConfigRoutesIpv6RowEditorInfoGroup OBJECT-GROUP
    OBJECTS     { gamIpConfigRoutesIpv6RowEditorNetworkAddress,
                  gamIpConfigRoutesIpv6RowEditorNetworkPrefixSize,
                  gamIpConfigRoutesIpv6RowEditorNextHop,
                  gamIpConfigRoutesIpv6RowEditorNextHopInterface,
                  gamIpConfigRoutesIpv6RowEditorAction }
    STATUS      current
    DESCRIPTION
        "A collection of objects."
    ::= { gamIpMibGroups 10 }

gamIpStatusGlobalsIpv4NeighbourInfoGroup OBJECT-GROUP
    OBJECTS     { gamIpStatusGlobalsIpv4NeighbourIpv4,
                  gamIpStatusGlobalsIpv4NeighbourMacAddress,
                  gamIpStatusGlobalsIpv4NeighbourInterface }
    STATUS      current
    DESCRIPTION
        "A collection of objects."
    ::= { gamIpMibGroups 11 }

gamIpStatusGlobalsIpv6NeighbourInfoGroup OBJECT-GROUP
    OBJECTS     { gamIpStatusGlobalsIpv6NeighbourIpAddress,
                  gamIpStatusGlobalsIpv6NeighbourInterfaceQuery,
                  gamIpStatusGlobalsIpv6NeighbourMacAddress,
                  gamIpStatusGlobalsIpv6NeighbourInterface }
    STATUS      current
    DESCRIPTION
        "A collection of objects."
    ::= { gamIpMibGroups 12 }

gamIpStatusInterfacesLinkInfoGroup OBJECT-GROUP
    OBJECTS     { gamIpStatusInterfacesLinkIfIndex,
                  gamIpStatusInterfacesLinkOsInterfaceIndex,
                  gamIpStatusInterfacesLinkMtu,
                  gamIpStatusInterfacesLinkMacAddress,
                  gamIpStatusInterfacesLinkUp,
                  gamIpStatusInterfacesLinkBroadcast,
                  gamIpStatusInterfacesLinkLoopback,
                  gamIpStatusInterfacesLinkRunning,
                  gamIpStatusInterfacesLinkNoarp,
                  gamIpStatusInterfacesLinkPromisc,
                  gamIpStatusInterfacesLinkMulticast }
    STATUS      current
    DESCRIPTION
        "A collection of objects."
    ::= { gamIpMibGroups 13 }

gamIpStatusInterfacesIpv4InfoGroup OBJECT-GROUP
    OBJECTS     { gamIpStatusInterfacesIpv4IfIndex,
                  gamIpStatusInterfacesIpv4NetworkAddress,
                  gamIpStatusInterfacesIpv4NetworkMaskLength,
                  gamIpStatusInterfacesIpv4Broadcast }
    STATUS      current
    DESCRIPTION
        "A collection of objects."
    ::= { gamIpMibGroups 14 }

gamIpStatusInterfacesDhcpClientV4InfoGroup OBJECT-GROUP
    OBJECTS     { gamIpStatusInterfacesDhcpClientV4IfIndex,
                  gamIpStatusInterfacesDhcpClientV4State,
                  gamIpStatusInterfacesDhcpClientV4ServerIp }
    STATUS      current
    DESCRIPTION
        "A collection of objects."
    ::= { gamIpMibGroups 15 }

gamIpStatusInterfacesIpv6InfoGroup OBJECT-GROUP
    OBJECTS     { gamIpStatusInterfacesIpv6IfIndex,
                  gamIpStatusInterfacesIpv6NetworkAddress,
                  gamIpStatusInterfacesIpv6NetworkMaskLength,
                  gamIpStatusInterfacesIpv6Tentative,
                  gamIpStatusInterfacesIpv6Duplicated,
                  gamIpStatusInterfacesIpv6Detached,
                  gamIpStatusInterfacesIpv6Nodad,
                  gamIpStatusInterfacesIpv6Autoconf }
    STATUS      current
    DESCRIPTION
        "A collection of objects."
    ::= { gamIpMibGroups 16 }

gamIpStatusRoutesIpv4InfoGroup OBJECT-GROUP
    OBJECTS     { gamIpStatusRoutesIpv4NetworkAddress,
                  gamIpStatusRoutesIpv4NetworkPrefixSize,
                  gamIpStatusRoutesIpv4NextHop,
                  gamIpStatusRoutesIpv4DerivedNextHopInterface,
                  gamIpStatusRoutesIpv4FlagUp,
                  gamIpStatusRoutesIpv4FlagHost,
                  gamIpStatusRoutesIpv4FlagGateway,
                  gamIpStatusRoutesIpv4OwnerConf,
                  gamIpStatusRoutesIpv4OwnerDhcp,
                  gamIpStatusRoutesIpv4OwnerDynamic }
    STATUS      current
    DESCRIPTION
        "A collection of objects."
    ::= { gamIpMibGroups 17 }

gamIpStatusRoutesIpv6InfoGroup OBJECT-GROUP
    OBJECTS     { gamIpStatusRoutesIpv6NetworkAddress,
                  gamIpStatusRoutesIpv6NetworkPrefixSize,
                  gamIpStatusRoutesIpv6NextHop,
                  gamIpStatusRoutesIpv6NextHopInterface,
                  gamIpStatusRoutesIpv6DerivedNextHopInterface,
                  gamIpStatusRoutesIpv6FlagUp,
                  gamIpStatusRoutesIpv6FlagHost,
                  gamIpStatusRoutesIpv6FlagGateway,
                  gamIpStatusRoutesIpv6OwnerConf,
                  gamIpStatusRoutesIpv6OwnerDhcp,
                  gamIpStatusRoutesIpv6OwnerDynamic }
    STATUS      current
    DESCRIPTION
        "A collection of objects."
    ::= { gamIpMibGroups 18 }

gamIpControlGlobalsInfoGroup OBJECT-GROUP
    OBJECTS     { gamIpControlGlobalsIpv4NeighbourTableClear,
                  gamIpControlGlobalsIpv6NeighbourTableClear,
                  gamIpControlGlobalsIpv4SystemStatisticsClear,
                  gamIpControlGlobalsIpv6SystemStatisticsClear,
                  gamIpControlGlobalsIpv4AcdStatusClear }
    STATUS      current
    DESCRIPTION
        "A collection of objects."
    ::= { gamIpMibGroups 19 }

gamIpControlInterfaceDhcpClientInfoGroup OBJECT-GROUP
    OBJECTS     { gamIpControlInterfaceDhcpClientIfIndex,
                  gamIpControlInterfaceDhcpClientRestart }
    STATUS      current
    DESCRIPTION
        "A collection of objects."
    ::= { gamIpMibGroups 20 }

gamIpStatisticsGlobalsIpv4InfoGroup OBJECT-GROUP
    OBJECTS     { gamIpStatisticsGlobalsIpv4InReceives,
                  gamIpStatisticsGlobalsIpv4HCInReceives,
                  gamIpStatisticsGlobalsIpv4InOctets,
                  gamIpStatisticsGlobalsIpv4HCInOctets,
                  gamIpStatisticsGlobalsIpv4InHdrErrors,
                  gamIpStatisticsGlobalsIpv4InNoRoutes,
                  gamIpStatisticsGlobalsIpv4InAddrErrors,
                  gamIpStatisticsGlobalsIpv4InUnknownProtos,
                  gamIpStatisticsGlobalsIpv4InTruncatedPkts,
                  gamIpStatisticsGlobalsIpv4InForwDatagrams,
                  gamIpStatisticsGlobalsIpv4HCInForwDatagrams,
                  gamIpStatisticsGlobalsIpv4ReasmReqds,
                  gamIpStatisticsGlobalsIpv4ReasmOKs,
                  gamIpStatisticsGlobalsIpv4ReasmFails,
                  gamIpStatisticsGlobalsIpv4InDiscards,
                  gamIpStatisticsGlobalsIpv4InDelivers,
                  gamIpStatisticsGlobalsIpv4HCInDelivers,
                  gamIpStatisticsGlobalsIpv4OutRequests,
                  gamIpStatisticsGlobalsIpv4HCOutRequests,
                  gamIpStatisticsGlobalsIpv4OutNoRoutes,
                  gamIpStatisticsGlobalsIpv4OutForwDatagrams,
                  gamIpStatisticsGlobalsIpv4HCOutForwDatagrams,
                  gamIpStatisticsGlobalsIpv4OutDiscards,
                  gamIpStatisticsGlobalsIpv4OutFragReqds,
                  gamIpStatisticsGlobalsIpv4OutFragOKs,
                  gamIpStatisticsGlobalsIpv4OutFragFails,
                  gamIpStatisticsGlobalsIpv4OutFragCreates,
                  gamIpStatisticsGlobalsIpv4OutTransmits,
                  gamIpStatisticsGlobalsIpv4HCOutTransmits,
                  gamIpStatisticsGlobalsIpv4OutOctets,
                  gamIpStatisticsGlobalsIpv4HCOutOctets,
                  gamIpStatisticsGlobalsIpv4InMcastPkts,
                  gamIpStatisticsGlobalsIpv4HCInMcastPkts,
                  gamIpStatisticsGlobalsIpv4InMcastOctets,
                  gamIpStatisticsGlobalsIpv4HCInMcastOctets,
                  gamIpStatisticsGlobalsIpv4OutMcastPkts,
                  gamIpStatisticsGlobalsIpv4HCOutMcastPkts,
                  gamIpStatisticsGlobalsIpv4OutMcastOctets,
                  gamIpStatisticsGlobalsIpv4HCOutMcastOctets,
                  gamIpStatisticsGlobalsIpv4InBcastPkts,
                  gamIpStatisticsGlobalsIpv4HCInBcastPkts,
                  gamIpStatisticsGlobalsIpv4OutBcastPkts,
                  gamIpStatisticsGlobalsIpv4HCOutBcastPkts,
                  gamIpStatisticsGlobalsIpv4DiscontinuityTime,
                  gamIpStatisticsGlobalsIpv4RefreshRate }
    STATUS      current
    DESCRIPTION
        "A collection of objects."
    ::= { gamIpMibGroups 21 }

gamIpStatisticsGlobalsIpv6InfoGroup OBJECT-GROUP
    OBJECTS     { gamIpStatisticsGlobalsIpv6InReceives,
                  gamIpStatisticsGlobalsIpv6HCInReceives,
                  gamIpStatisticsGlobalsIpv6InOctets,
                  gamIpStatisticsGlobalsIpv6HCInOctets,
                  gamIpStatisticsGlobalsIpv6InHdrErrors,
                  gamIpStatisticsGlobalsIpv6InNoRoutes,
                  gamIpStatisticsGlobalsIpv6InAddrErrors,
                  gamIpStatisticsGlobalsIpv6InUnknownProtos,
                  gamIpStatisticsGlobalsIpv6InTruncatedPkts,
                  gamIpStatisticsGlobalsIpv6InForwDatagrams,
                  gamIpStatisticsGlobalsIpv6HCInForwDatagrams,
                  gamIpStatisticsGlobalsIpv6ReasmReqds,
                  gamIpStatisticsGlobalsIpv6ReasmOKs,
                  gamIpStatisticsGlobalsIpv6ReasmFails,
                  gamIpStatisticsGlobalsIpv6InDiscards,
                  gamIpStatisticsGlobalsIpv6InDelivers,
                  gamIpStatisticsGlobalsIpv6HCInDelivers,
                  gamIpStatisticsGlobalsIpv6OutRequests,
                  gamIpStatisticsGlobalsIpv6HCOutRequests,
                  gamIpStatisticsGlobalsIpv6OutNoRoutes,
                  gamIpStatisticsGlobalsIpv6OutForwDatagrams,
                  gamIpStatisticsGlobalsIpv6HCOutForwDatagrams,
                  gamIpStatisticsGlobalsIpv6OutDiscards,
                  gamIpStatisticsGlobalsIpv6OutFragReqds,
                  gamIpStatisticsGlobalsIpv6OutFragOKs,
                  gamIpStatisticsGlobalsIpv6OutFragFails,
                  gamIpStatisticsGlobalsIpv6OutFragCreates,
                  gamIpStatisticsGlobalsIpv6OutTransmits,
                  gamIpStatisticsGlobalsIpv6HCOutTransmits,
                  gamIpStatisticsGlobalsIpv6OutOctets,
                  gamIpStatisticsGlobalsIpv6HCOutOctets,
                  gamIpStatisticsGlobalsIpv6InMcastPkts,
                  gamIpStatisticsGlobalsIpv6HCInMcastPkts,
                  gamIpStatisticsGlobalsIpv6InMcastOctets,
                  gamIpStatisticsGlobalsIpv6HCInMcastOctets,
                  gamIpStatisticsGlobalsIpv6OutMcastPkts,
                  gamIpStatisticsGlobalsIpv6HCOutMcastPkts,
                  gamIpStatisticsGlobalsIpv6OutMcastOctets,
                  gamIpStatisticsGlobalsIpv6HCOutMcastOctets,
                  gamIpStatisticsGlobalsIpv6InBcastPkts,
                  gamIpStatisticsGlobalsIpv6HCInBcastPkts,
                  gamIpStatisticsGlobalsIpv6OutBcastPkts,
                  gamIpStatisticsGlobalsIpv6HCOutBcastPkts,
                  gamIpStatisticsGlobalsIpv6DiscontinuityTime,
                  gamIpStatisticsGlobalsIpv6RefreshRate }
    STATUS      current
    DESCRIPTION
        "A collection of objects."
    ::= { gamIpMibGroups 22 }

gamIpStatisticsInterfacesLinkInfoGroup OBJECT-GROUP
    OBJECTS     { gamIpStatisticsInterfacesLinkIfIndex,
                  gamIpStatisticsInterfacesLinkInPackets,
                  gamIpStatisticsInterfacesLinkOutPackets,
                  gamIpStatisticsInterfacesLinkInBytes,
                  gamIpStatisticsInterfacesLinkOutBytes,
                  gamIpStatisticsInterfacesLinkInMulticasts,
                  gamIpStatisticsInterfacesLinkOutMulticasts,
                  gamIpStatisticsInterfacesLinkInBroadcasts,
                  gamIpStatisticsInterfacesLinkOutBroadcasts }
    STATUS      current
    DESCRIPTION
        "A collection of objects."
    ::= { gamIpMibGroups 23 }

gamIpStatisticsInterfacesIpv4InfoGroup OBJECT-GROUP
    OBJECTS     { gamIpStatisticsInterfacesIpv4IfIndex,
                  gamIpStatisticsInterfacesIpv4InReceives,
                  gamIpStatisticsInterfacesIpv4HCInReceives,
                  gamIpStatisticsInterfacesIpv4InOctets,
                  gamIpStatisticsInterfacesIpv4HCInOctets,
                  gamIpStatisticsInterfacesIpv4InHdrErrors,
                  gamIpStatisticsInterfacesIpv4InNoRoutes,
                  gamIpStatisticsInterfacesIpv4InAddrErrors,
                  gamIpStatisticsInterfacesIpv4InUnknownProtos,
                  gamIpStatisticsInterfacesIpv4InTruncatedPkts,
                  gamIpStatisticsInterfacesIpv4InForwDatagrams,
                  gamIpStatisticsInterfacesIpv4HCInForwDatagrams,
                  gamIpStatisticsInterfacesIpv4ReasmReqds,
                  gamIpStatisticsInterfacesIpv4ReasmOKs,
                  gamIpStatisticsInterfacesIpv4ReasmFails,
                  gamIpStatisticsInterfacesIpv4InDiscards,
                  gamIpStatisticsInterfacesIpv4InDelivers,
                  gamIpStatisticsInterfacesIpv4HCInDelivers,
                  gamIpStatisticsInterfacesIpv4OutRequests,
                  gamIpStatisticsInterfacesIpv4HCOutRequests,
                  gamIpStatisticsInterfacesIpv4OutNoRoutes,
                  gamIpStatisticsInterfacesIpv4OutForwDatagrams,
                  gamIpStatisticsInterfacesIpv4HCOutForwDatagrams,
                  gamIpStatisticsInterfacesIpv4OutDiscards,
                  gamIpStatisticsInterfacesIpv4OutFragReqds,
                  gamIpStatisticsInterfacesIpv4OutFragOKs,
                  gamIpStatisticsInterfacesIpv4OutFragFails,
                  gamIpStatisticsInterfacesIpv4OutFragCreates,
                  gamIpStatisticsInterfacesIpv4OutTransmits,
                  gamIpStatisticsInterfacesIpv4HCOutTransmits,
                  gamIpStatisticsInterfacesIpv4OutOctets,
                  gamIpStatisticsInterfacesIpv4HCOutOctets,
                  gamIpStatisticsInterfacesIpv4InMcastPkts,
                  gamIpStatisticsInterfacesIpv4HCInMcastPkts,
                  gamIpStatisticsInterfacesIpv4InMcastOctets,
                  gamIpStatisticsInterfacesIpv4HCInMcastOctets,
                  gamIpStatisticsInterfacesIpv4OutMcastPkts,
                  gamIpStatisticsInterfacesIpv4HCOutMcastPkts,
                  gamIpStatisticsInterfacesIpv4OutMcastOctets,
                  gamIpStatisticsInterfacesIpv4HCOutMcastOctets,
                  gamIpStatisticsInterfacesIpv4InBcastPkts,
                  gamIpStatisticsInterfacesIpv4HCInBcastPkts,
                  gamIpStatisticsInterfacesIpv4OutBcastPkts,
                  gamIpStatisticsInterfacesIpv4HCOutBcastPkts,
                  gamIpStatisticsInterfacesIpv4DiscontinuityTime,
                  gamIpStatisticsInterfacesIpv4RefreshRate }
    STATUS      current
    DESCRIPTION
        "A collection of objects."
    ::= { gamIpMibGroups 24 }

gamIpStatisticsInterfacesIpv6InfoGroup OBJECT-GROUP
    OBJECTS     { gamIpStatisticsInterfacesIpv6IfIndex,
                  gamIpStatisticsInterfacesIpv6InReceives,
                  gamIpStatisticsInterfacesIpv6HCInReceives,
                  gamIpStatisticsInterfacesIpv6InOctets,
                  gamIpStatisticsInterfacesIpv6HCInOctets,
                  gamIpStatisticsInterfacesIpv6InHdrErrors,
                  gamIpStatisticsInterfacesIpv6InNoRoutes,
                  gamIpStatisticsInterfacesIpv6InAddrErrors,
                  gamIpStatisticsInterfacesIpv6InUnknownProtos,
                  gamIpStatisticsInterfacesIpv6InTruncatedPkts,
                  gamIpStatisticsInterfacesIpv6InForwDatagrams,
                  gamIpStatisticsInterfacesIpv6HCInForwDatagrams,
                  gamIpStatisticsInterfacesIpv6ReasmReqds,
                  gamIpStatisticsInterfacesIpv6ReasmOKs,
                  gamIpStatisticsInterfacesIpv6ReasmFails,
                  gamIpStatisticsInterfacesIpv6InDiscards,
                  gamIpStatisticsInterfacesIpv6InDelivers,
                  gamIpStatisticsInterfacesIpv6HCInDelivers,
                  gamIpStatisticsInterfacesIpv6OutRequests,
                  gamIpStatisticsInterfacesIpv6HCOutRequests,
                  gamIpStatisticsInterfacesIpv6OutNoRoutes,
                  gamIpStatisticsInterfacesIpv6OutForwDatagrams,
                  gamIpStatisticsInterfacesIpv6HCOutForwDatagrams,
                  gamIpStatisticsInterfacesIpv6OutDiscards,
                  gamIpStatisticsInterfacesIpv6OutFragReqds,
                  gamIpStatisticsInterfacesIpv6OutFragOKs,
                  gamIpStatisticsInterfacesIpv6OutFragFails,
                  gamIpStatisticsInterfacesIpv6OutFragCreates,
                  gamIpStatisticsInterfacesIpv6OutTransmits,
                  gamIpStatisticsInterfacesIpv6HCOutTransmits,
                  gamIpStatisticsInterfacesIpv6OutOctets,
                  gamIpStatisticsInterfacesIpv6HCOutOctets,
                  gamIpStatisticsInterfacesIpv6InMcastPkts,
                  gamIpStatisticsInterfacesIpv6HCInMcastPkts,
                  gamIpStatisticsInterfacesIpv6InMcastOctets,
                  gamIpStatisticsInterfacesIpv6HCInMcastOctets,
                  gamIpStatisticsInterfacesIpv6OutMcastPkts,
                  gamIpStatisticsInterfacesIpv6HCOutMcastPkts,
                  gamIpStatisticsInterfacesIpv6OutMcastOctets,
                  gamIpStatisticsInterfacesIpv6HCOutMcastOctets,
                  gamIpStatisticsInterfacesIpv6InBcastPkts,
                  gamIpStatisticsInterfacesIpv6HCInBcastPkts,
                  gamIpStatisticsInterfacesIpv6OutBcastPkts,
                  gamIpStatisticsInterfacesIpv6HCOutBcastPkts,
                  gamIpStatisticsInterfacesIpv6DiscontinuityTime,
                  gamIpStatisticsInterfacesIpv6RefreshRate }
    STATUS      current
    DESCRIPTION
        "A collection of objects."
    ::= { gamIpMibGroups 25 }

gamIpTrapInterfacesLinkAddInfoGroup NOTIFICATION-GROUP
    NOTIFICATIONS { gamIpTrapInterfacesLinkAdd }
    STATUS      current
    DESCRIPTION
        "Information group containing a trap."
    ::= { gamIpMibGroups 26 }

gamIpTrapInterfacesLinkModInfoGroup NOTIFICATION-GROUP
    NOTIFICATIONS { gamIpTrapInterfacesLinkMod }
    STATUS      current
    DESCRIPTION
        "Information group containing a trap."
    ::= { gamIpMibGroups 27 }

gamIpTrapInterfacesLinkDelInfoGroup NOTIFICATION-GROUP
    NOTIFICATIONS { gamIpTrapInterfacesLinkDel }
    STATUS      current
    DESCRIPTION
        "Information group containing a trap."
    ::= { gamIpMibGroups 28 }

gamIpMibCompliance MODULE-COMPLIANCE
    STATUS      current
    DESCRIPTION
        "The compliance statement for the implementation."

    MODULE      -- this module

    MANDATORY-GROUPS { gamIpCapabilitiesInfoGroup,
                       gamIpConfigGlobalsMainInfoGroup,
                       gamIpConfigInterfacesTableInfoGroup,
                       gamIpConfigInterfacesTableRowEditorInfoGroup,
                       gamIpConfigInterfacesIpv4TableInfoGroup,
                       gamIpConfigInterfacesIpv6TableInfoGroup,
                       gamIpConfigRoutesIpv4TableInfoGroup,
                       gamIpConfigRoutesIpv4RowEditorInfoGroup,
                       gamIpConfigRoutesIpv6TableInfoGroup,
                       gamIpConfigRoutesIpv6RowEditorInfoGroup,
                       gamIpStatusGlobalsIpv4NeighbourInfoGroup,
                       gamIpStatusGlobalsIpv6NeighbourInfoGroup,
                       gamIpStatusInterfacesLinkInfoGroup,
                       gamIpStatusInterfacesIpv4InfoGroup,
                       gamIpStatusInterfacesDhcpClientV4InfoGroup,
                       gamIpStatusInterfacesIpv6InfoGroup,
                       gamIpStatusRoutesIpv4InfoGroup,
                       gamIpStatusRoutesIpv6InfoGroup,
                       gamIpControlGlobalsInfoGroup,
                       gamIpControlInterfaceDhcpClientInfoGroup,
                       gamIpStatisticsGlobalsIpv4InfoGroup,
                       gamIpStatisticsGlobalsIpv6InfoGroup,
                       gamIpStatisticsInterfacesLinkInfoGroup,
                       gamIpStatisticsInterfacesIpv4InfoGroup,
                       gamIpStatisticsInterfacesIpv6InfoGroup,
                       gamIpTrapInterfacesLinkAddInfoGroup,
                       gamIpTrapInterfacesLinkModInfoGroup,
                       gamIpTrapInterfacesLinkDelInfoGroup }

    ::= { gamIpMibCompliances 1 }

END
