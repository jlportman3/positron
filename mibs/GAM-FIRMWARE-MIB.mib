-- *****************************************************************
-- FIRMWARE-MIB:  Positron's GAM private MIB
-- *****************************************************************

GAM-FIRMWARE-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    GAMDisplayString FROM GAM-TC
    Integer32 FROM SNMPv2-SMI
    Unsigned32 FROM SNMPv2-SMI
    TruthValue FROM SNMPv2-TC
    ;

gamFirmwareMib MODULE-IDENTITY
    LAST-UPDATED "201702030000Z"
    ORGANIZATION
        "Positron Access Solutions Corp."
    CONTACT-INFO
        "Customer Service <info@positronaccess.com>"
    DESCRIPTION
        "This is a private version of Firmware"
    REVISION    "201702030000Z"
    DESCRIPTION
        "Replaced firmware upload status message 'Incorrect image version' with
         'Incompatible target'"
    REVISION    "201605310000Z"
    DESCRIPTION
        "Enhanced firmware upload status messages"
    REVISION    "201412160000Z"
    DESCRIPTION
        "Add switch table"
    REVISION    "201410100000Z"
    DESCRIPTION
        "Editorial changes"
    REVISION    "201407010000Z"
    DESCRIPTION
        "Initial version"
    ::= { gamMgmt 28 }


GAMFirmwareStatusImageEnum ::= TEXTUAL-CONVENTION
    STATUS      current
    DESCRIPTION
        "This enumeration defines the type of image for status."
    SYNTAX      INTEGER { bootloader(0), activeFirmware(1),
                          alternativeFirmware(2) }

GAMFirmwareUploadImageEnum ::= TEXTUAL-CONVENTION
    STATUS      current
    DESCRIPTION
        "This enumeration defines the type of image to upload."
    SYNTAX      INTEGER { bootloader(0), firmware(1) }

GAMFirmwareUploadStatusEnum ::= TEXTUAL-CONVENTION
    STATUS      current
    DESCRIPTION
        "This enumeration defines the status of upload operation."
    SYNTAX      INTEGER { none(0), success(1), inProgress(2),
                          errIvalidIp(3), errTftpFailed(4),
                          errBusy(5), errMemoryInsufficient(6),
                          errInvalidImage(7), errWriteFlash(8),
                          errSameImageExisted(9), errUnknownImage(10),
                          errFlashImageNotFound(11),
                          errFlashEntryNotFound(12), errCrc(13),
                          errImageSize(14), errEraseFlash(15),
                          errIncompatibleTarget(16),
                          errDownloadUrl(17), errInvalidUrl(18),
                          errInvalidPath(19), errInvalidFilename(20) }

gamFirmwareMibObjects OBJECT IDENTIFIER
    ::= { gamFirmwareMib 1 }

gamFirmwareStatus OBJECT IDENTIFIER
    ::= { gamFirmwareMibObjects 3 }

gamFirmwareStatusImageTable OBJECT-TYPE
    SYNTAX      SEQUENCE OF GAMFirmwareStatusImageEntry
    MAX-ACCESS  not-accessible
    STATUS      current
    DESCRIPTION
        "This is a table of status of images in flash."
    ::= { gamFirmwareStatus 1 }

gamFirmwareStatusImageEntry OBJECT-TYPE
    SYNTAX      GAMFirmwareStatusImageEntry
    MAX-ACCESS  not-accessible
    STATUS      current
    DESCRIPTION
        "Each entry has a set of image status."
    INDEX       { gamFirmwareStatusImageNumber }
    ::= { gamFirmwareStatusImageTable 1 }

GAMFirmwareStatusImageEntry ::= SEQUENCE {
    gamFirmwareStatusImageNumber           Integer32,
    gamFirmwareStatusImageType             GAMFirmwareStatusImageEnum,
    gamFirmwareStatusImageName             GAMDisplayString,
    gamFirmwareStatusImageVersion          GAMDisplayString,
    gamFirmwareStatusImageBuiltDate        GAMDisplayString,
    gamFirmwareStatusImageCodeRevision     GAMDisplayString,
    gamFirmwareStatusImageNorFlashSupport  GAMDisplayString,
    gamFirmwareStatusImageMgmtPhySupport   GAMDisplayString
}

gamFirmwareStatusImageNumber OBJECT-TYPE
    SYNTAX      Integer32 (0..2)
    MAX-ACCESS  accessible-for-notify
    STATUS      current
    DESCRIPTION
        "The number of image. The number starts from 0."
    ::= { gamFirmwareStatusImageEntry 1 }

gamFirmwareStatusImageType OBJECT-TYPE
    SYNTAX      GAMFirmwareStatusImageEnum
    MAX-ACCESS  read-only
    STATUS      current
    DESCRIPTION
        "Image type of the status. bootloader(0) is for boot loader.
         activeFirmware(1) is for active (primary) firmware.
         alternativeFirmware(2) is for alternative (backup) firmware."
    ::= { gamFirmwareStatusImageEntry 2 }

gamFirmwareStatusImageName OBJECT-TYPE
    SYNTAX      GAMDisplayString (SIZE(0..127))
    MAX-ACCESS  read-only
    STATUS      current
    DESCRIPTION
        "Image name."
    ::= { gamFirmwareStatusImageEntry 3 }

gamFirmwareStatusImageVersion OBJECT-TYPE
    SYNTAX      GAMDisplayString (SIZE(0..255))
    MAX-ACCESS  read-only
    STATUS      current
    DESCRIPTION
        "Image version."
    ::= { gamFirmwareStatusImageEntry 4 }

gamFirmwareStatusImageBuiltDate OBJECT-TYPE
    SYNTAX      GAMDisplayString (SIZE(0..255))
    MAX-ACCESS  read-only
    STATUS      current
    DESCRIPTION
        "The built date when the image is built."
    ::= { gamFirmwareStatusImageEntry 5 }

gamFirmwareStatusImageCodeRevision OBJECT-TYPE
    SYNTAX      GAMDisplayString (SIZE(0..127))
    MAX-ACCESS  read-only
    STATUS      current
    DESCRIPTION
        "The code revesion which the image is built."
    ::= { gamFirmwareStatusImageEntry 6 }

gamFirmwareStatusImageNorFlashSupport OBJECT-TYPE
    SYNTAX      GAMDisplayString (SIZE(0..255))
    MAX-ACCESS  read-only
    STATUS      current
    DESCRIPTION
        "The NOR flash supported by this image. This image can only be installed
         on GAM having one of those NOR flash models."
    ::= { gamFirmwareStatusImageEntry 7 }

gamFirmwareStatusImageMgmtPhySupport OBJECT-TYPE
    SYNTAX      GAMDisplayString (SIZE(0..255))
    MAX-ACCESS  read-only
    STATUS      current
    DESCRIPTION
        "The management port PHY supported by this image. This image can only be
         installed on GAM having one of those MGMT PHY models."
    ::= { gamFirmwareStatusImageEntry 8 }

gamFirmwareStatusImageUpload OBJECT IDENTIFIER
    ::= { gamFirmwareStatus 2 }

gamFirmwareStatusImageUploadStatus OBJECT-TYPE
    SYNTAX      GAMFirmwareUploadStatusEnum
    MAX-ACCESS  read-only
    STATUS      current
    DESCRIPTION
        "The status indicates the status of current upload operation. It is
         updated automatically. Modifying this flag does not take any effect.
         none(0) means no upload operation. success(1) means upload operation is
         successful. inProgress(2) means current upload operation is in
         progress. errIvalidIp(3) means upload operation is failed due to
         invalid IP address. errTftpFailed(4) means upload operation is failed
         due to failed TFTP operation. errBusy(5) means upload operation is
         failed due to other upload in processing. errMemoryInsufficient(6)
         means upload operation is failed due to memory insufficient.
         errInvalidImage(7) means upload operation is failed due to invalid
         image. errWriteFlash(8) means upload operation is failed due to failed
         writing flash. errSameImageExisted(9) means upload operation is failed
         because the upload image is the same as the one in flash.
         errUnknownImage(10) means upload operation is failed because the type
         of upload image is unknown. errFlashImageNotFound(11) means upload
         operation is failed because the location in flash to upload the image
         is not found. errFlashEntryNotFound(12) means upload operation is
         failed because the corresponding entry in flash to upload the image is
         not found. errCrc(13) means upload operation is failed due to incorrect
         CRC in the upload image. errImageSize(14) means upload operation is
         failed due to invalid image size. errEraseFlash(15) means upload
         operation is failed due to failed erasing flash.
         errIncorrectImageVersion(16) means upload operation is failed due to
         incorrect version of the upload image. errDownloadUrl(17) means upload
         operation is failed due to fail to download image from URL.
         errInvalidUrl(18) means upload operation is failed due to invalid URL.
         errInvalidFilename(19) means upload operation is failed due to invalid
         filename of the upload image. errInvalidPath(20) means upload operation
         is failed due to invalid path of the upload image. "
    ::= { gamFirmwareStatusImageUpload 1 }

gamFirmwareStatusSwitchTable OBJECT-TYPE
    SYNTAX      SEQUENCE OF GAMFirmwareStatusSwitchEntry
    MAX-ACCESS  not-accessible
    STATUS      current
    DESCRIPTION
        "This is a table of status of images in switch."
    ::= { gamFirmwareStatus 3 }

gamFirmwareStatusSwitchEntry OBJECT-TYPE
    SYNTAX      GAMFirmwareStatusSwitchEntry
    MAX-ACCESS  not-accessible
    STATUS      current
    DESCRIPTION
        "Each entry has a set of image status."
    INDEX       { gamFirmwareStatusSwitchSwitchId }
    ::= { gamFirmwareStatusSwitchTable 1 }

GAMFirmwareStatusSwitchEntry ::= SEQUENCE {
    gamFirmwareStatusSwitchSwitchId         Integer32,
    gamFirmwareStatusSwitchChipId           GAMDisplayString,
    gamFirmwareStatusSwitchBoardType        GAMDisplayString,
    gamFirmwareStatusSwitchPortCnt          Unsigned32,
    gamFirmwareStatusSwitchProduct          GAMDisplayString,
    gamFirmwareStatusSwitchVersion          GAMDisplayString,
    gamFirmwareStatusSwitchBuiltDate        GAMDisplayString,
    gamFirmwareStatusSwitchNorFlashSupport  GAMDisplayString,
    gamFirmwareStatusSwitchMgmtPhySupport   GAMDisplayString
}

gamFirmwareStatusSwitchSwitchId OBJECT-TYPE
    SYNTAX      Integer32 (1..16)
    MAX-ACCESS  accessible-for-notify
    STATUS      current
    DESCRIPTION
        "The ID of switch."
    ::= { gamFirmwareStatusSwitchEntry 1 }

gamFirmwareStatusSwitchChipId OBJECT-TYPE
    SYNTAX      GAMDisplayString (SIZE(0..31))
    MAX-ACCESS  read-only
    STATUS      current
    DESCRIPTION
        "ID of chip."
    ::= { gamFirmwareStatusSwitchEntry 2 }

gamFirmwareStatusSwitchBoardType OBJECT-TYPE
    SYNTAX      GAMDisplayString (SIZE(0..63))
    MAX-ACCESS  read-only
    STATUS      current
    DESCRIPTION
        "Type of board."
    ::= { gamFirmwareStatusSwitchEntry 3 }

gamFirmwareStatusSwitchPortCnt OBJECT-TYPE
    SYNTAX      Unsigned32
    MAX-ACCESS  read-only
    STATUS      current
    DESCRIPTION
        "Count of ports."
    ::= { gamFirmwareStatusSwitchEntry 4 }

gamFirmwareStatusSwitchProduct OBJECT-TYPE
    SYNTAX      GAMDisplayString (SIZE(0..63))
    MAX-ACCESS  read-only
    STATUS      current
    DESCRIPTION
        "Product name."
    ::= { gamFirmwareStatusSwitchEntry 5 }

gamFirmwareStatusSwitchVersion OBJECT-TYPE
    SYNTAX      GAMDisplayString (SIZE(0..255))
    MAX-ACCESS  read-only
    STATUS      current
    DESCRIPTION
        "Image version."
    ::= { gamFirmwareStatusSwitchEntry 6 }

gamFirmwareStatusSwitchBuiltDate OBJECT-TYPE
    SYNTAX      GAMDisplayString (SIZE(0..255))
    MAX-ACCESS  read-only
    STATUS      current
    DESCRIPTION
        "The built date when the image is built."
    ::= { gamFirmwareStatusSwitchEntry 7 }

gamFirmwareStatusSwitchNorFlashSupport OBJECT-TYPE
    SYNTAX      GAMDisplayString (SIZE(0..255))
    MAX-ACCESS  read-only
    STATUS      current
    DESCRIPTION
        "The NOR flash supported by this image. This image can only be installed
         on GAM having one of those NOR flash models."
    ::= { gamFirmwareStatusSwitchEntry 8 }

gamFirmwareStatusSwitchMgmtPhySupport OBJECT-TYPE
    SYNTAX      GAMDisplayString (SIZE(0..255))
    MAX-ACCESS  read-only
    STATUS      current
    DESCRIPTION
        "The management port PHY supported by this image. This image can only be
         installed on GAM having one of those MGMT PHY models."
    ::= { gamFirmwareStatusSwitchEntry 9 }

gamFirmwareControl OBJECT IDENTIFIER
    ::= { gamFirmwareMibObjects 4 }

gamFirmwareControlGlobals OBJECT IDENTIFIER
    ::= { gamFirmwareControl 1 }

gamFirmwareControlGlobalsSwapFirmware OBJECT-TYPE
    SYNTAX      TruthValue
    MAX-ACCESS  read-write
    STATUS      current
    DESCRIPTION
        "Swap firmware between active (primary) and alternative (backup). true
         is to swap the firmware. false is to do nothing."
    ::= { gamFirmwareControlGlobals 1 }

gamFirmwareControlImageUpload OBJECT IDENTIFIER
    ::= { gamFirmwareControl 2 }

gamFirmwareControlImageUploadDoUpload OBJECT-TYPE
    SYNTAX      TruthValue
    MAX-ACCESS  read-write
    STATUS      current
    DESCRIPTION
        "Action to do upload image or not. true is to do the upload operation.
         false is to do nothing. The upload operation may need longer time to
         upload the image, so the SNMP timeout time needs to be modified
         accordingly."
    ::= { gamFirmwareControlImageUpload 1 }

gamFirmwareControlImageUploadImageType OBJECT-TYPE
    SYNTAX      GAMFirmwareUploadImageEnum
    MAX-ACCESS  read-write
    STATUS      current
    DESCRIPTION
        "Type of image to upload. bootloader(0) is to upload bootloader.
         firmware(1) is to upload application firmware."
    ::= { gamFirmwareControlImageUpload 2 }

gamFirmwareControlImageUploadUrl OBJECT-TYPE
    SYNTAX      GAMDisplayString (SIZE(0..255))
    MAX-ACCESS  read-write
    STATUS      current
    DESCRIPTION
        "The location of image to upload. It is a specific character string that
         constitutes a reference to a resource. Syntax:
         <protocol>://[<username>[:<password>]@]<host>[:<port>][/<path>]/<file_name>
         For example, tftp://10.10.10.10/new_image_path/new_image.dat,
         http://username:password@10.10.10.10:80/new_image_path/new_image.dat. A
         valid file name is a text string drawn from alphabet (A-Za-z), digits
         (0-9), dot (.), hyphen (-), under score(_). The maximum length is 63
         and hyphen must not be first character. The file name content that only
         contains '.' is not allowed."
    ::= { gamFirmwareControlImageUpload 3 }

gamFirmwareMibConformance OBJECT IDENTIFIER
    ::= { gamFirmwareMib 2 }

gamFirmwareMibCompliances OBJECT IDENTIFIER
    ::= { gamFirmwareMibConformance 1 }

gamFirmwareMibGroups OBJECT IDENTIFIER
    ::= { gamFirmwareMibConformance 2 }

gamFirmwareStatusImageTableInfoGroup OBJECT-GROUP
    OBJECTS     { gamFirmwareStatusImageNumber,
                  gamFirmwareStatusImageType,
                  gamFirmwareStatusImageName,
                  gamFirmwareStatusImageVersion,
                  gamFirmwareStatusImageBuiltDate,
                  gamFirmwareStatusImageCodeRevision,
                  gamFirmwareStatusImageNorFlashSupport,
                  gamFirmwareStatusImageMgmtPhySupport }
    STATUS      current
    DESCRIPTION
        "A collection of objects."
    ::= { gamFirmwareMibGroups 1 }

gamFirmwareStatusImageUploadInfoGroup OBJECT-GROUP
    OBJECTS     { gamFirmwareStatusImageUploadStatus }
    STATUS      current
    DESCRIPTION
        "A collection of objects."
    ::= { gamFirmwareMibGroups 2 }

gamFirmwareStatusSwitchTableInfoGroup OBJECT-GROUP
    OBJECTS     { gamFirmwareStatusSwitchSwitchId,
                  gamFirmwareStatusSwitchChipId,
                  gamFirmwareStatusSwitchBoardType,
                  gamFirmwareStatusSwitchPortCnt,
                  gamFirmwareStatusSwitchProduct,
                  gamFirmwareStatusSwitchVersion,
                  gamFirmwareStatusSwitchBuiltDate,
                  gamFirmwareStatusSwitchNorFlashSupport,
                  gamFirmwareStatusSwitchMgmtPhySupport }
    STATUS      current
    DESCRIPTION
        "A collection of objects."
    ::= { gamFirmwareMibGroups 3 }

gamFirmwareControlGlobalsInfoGroup OBJECT-GROUP
    OBJECTS     { gamFirmwareControlGlobalsSwapFirmware }
    STATUS      current
    DESCRIPTION
        "A collection of objects."
    ::= { gamFirmwareMibGroups 4 }

gamFirmwareControlImageUploadInfoGroup OBJECT-GROUP
    OBJECTS     { gamFirmwareControlImageUploadDoUpload,
                  gamFirmwareControlImageUploadImageType,
                  gamFirmwareControlImageUploadUrl }
    STATUS      current
    DESCRIPTION
        "A collection of objects."
    ::= { gamFirmwareMibGroups 5 }

gamFirmwareMibCompliance MODULE-COMPLIANCE
    STATUS      current
    DESCRIPTION
        "The compliance statement for the implementation."

    MODULE      -- this module

    MANDATORY-GROUPS { gamFirmwareStatusImageTableInfoGroup,
                       gamFirmwareStatusImageUploadInfoGroup,
                       gamFirmwareStatusSwitchTableInfoGroup,
                       gamFirmwareControlGlobalsInfoGroup,
                       gamFirmwareControlImageUploadInfoGroup }

    ::= { gamFirmwareMibCompliances 1 }

END
