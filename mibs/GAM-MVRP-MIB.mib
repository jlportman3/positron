-- *****************************************************************
-- MVRP-MIB:  Positron's GAM private MIB
-- *****************************************************************

GAM-MVRP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    GAMInterfaceIndex FROM GAM-TC
    GAMVlanListQuarter FROM GAM-TC
    Counter64 FROM SNMPv2-SMI
    MacAddress FROM SNMPv2-TC
    TruthValue FROM SNMPv2-TC
    ;

gamMvrpMib MODULE-IDENTITY
    LAST-UPDATED "201510190000Z"
    ORGANIZATION
        "Positron Access Solutions Corp."
    CONTACT-INFO
        "Customer Service <info@positronaccess.com>"
    DESCRIPTION
        "Private MVRP MIB."
    REVISION    "201510190000Z"
    DESCRIPTION
        "Initial version"
    ::= { gamMgmt 87 }


gamMvrpMibObjects OBJECT IDENTIFIER
    ::= { gamMvrpMib 1 }

gamMvrpConfig OBJECT IDENTIFIER
    ::= { gamMvrpMibObjects 2 }

gamMvrpConfigGlobals OBJECT IDENTIFIER
    ::= { gamMvrpConfig 1 }

gamMvrpConfigGlobalsGlobalState OBJECT-TYPE
    SYNTAX      TruthValue
    MAX-ACCESS  read-write
    STATUS      current
    DESCRIPTION
        "Global state of MVRP. TRUE - enable MVRP, FALSE - disable MVRP."
    ::= { gamMvrpConfigGlobals 1 }

gamMvrpConfigGlobalsManagedVlans0KTo1K OBJECT-TYPE
    SYNTAX      GAMVlanListQuarter
    MAX-ACCESS  read-write
    STATUS      current
    DESCRIPTION
        "First quarter of bit-array indicating the MVRP-managed VLANs."
    ::= { gamMvrpConfigGlobals 2 }

gamMvrpConfigGlobalsManagedVlans1KTo2K OBJECT-TYPE
    SYNTAX      GAMVlanListQuarter
    MAX-ACCESS  read-write
    STATUS      current
    DESCRIPTION
        "Second quarter of bit-array indicating the MVRP-managed VLANs."
    ::= { gamMvrpConfigGlobals 3 }

gamMvrpConfigGlobalsManagedVlans2KTo3K OBJECT-TYPE
    SYNTAX      GAMVlanListQuarter
    MAX-ACCESS  read-write
    STATUS      current
    DESCRIPTION
        "Third quarter of bit-array indicating the MVRP-managed VLANs."
    ::= { gamMvrpConfigGlobals 4 }

gamMvrpConfigGlobalsManagedVlans3KTo4K OBJECT-TYPE
    SYNTAX      GAMVlanListQuarter
    MAX-ACCESS  read-write
    STATUS      current
    DESCRIPTION
        "Last quarter of bit-array indicating the MVRP-managed VLANs."
    ::= { gamMvrpConfigGlobals 5 }

gamMvrpConfigInterface OBJECT IDENTIFIER
    ::= { gamMvrpConfig 2 }

gamMvrpConfigInterfaceTable OBJECT-TYPE
    SYNTAX      SEQUENCE OF GAMMvrpConfigInterfaceEntry
    MAX-ACCESS  not-accessible
    STATUS      current
    DESCRIPTION
        "This is the MVRP interface configuration table. The number of
         interfaces is the total number of ports available on the switch/stack.
         Each one of these interfaces can be set to either MVRP enabled or MVRP
         disabled."
    ::= { gamMvrpConfigInterface 1 }

gamMvrpConfigInterfaceEntry OBJECT-TYPE
    SYNTAX      GAMMvrpConfigInterfaceEntry
    MAX-ACCESS  not-accessible
    STATUS      current
    DESCRIPTION
        "Entries in this table represent switch interfaces and their
         corresponding MVRP state"
    INDEX       { gamMvrpConfigInterfaceIfIndex }
    ::= { gamMvrpConfigInterfaceTable 1 }

GAMMvrpConfigInterfaceEntry ::= SEQUENCE {
    gamMvrpConfigInterfaceIfIndex    GAMInterfaceIndex,
    gamMvrpConfigInterfacePortState  TruthValue
}

gamMvrpConfigInterfaceIfIndex OBJECT-TYPE
    SYNTAX      GAMInterfaceIndex
    MAX-ACCESS  accessible-for-notify
    STATUS      current
    DESCRIPTION
        "Interface index number."
    ::= { gamMvrpConfigInterfaceEntry 1 }

gamMvrpConfigInterfacePortState OBJECT-TYPE
    SYNTAX      TruthValue
    MAX-ACCESS  read-write
    STATUS      current
    DESCRIPTION
        "Per-interface state of MVRP. TRUE - enable MVRP on the interface, FALSE
         - disable MVRP on the interface."
    ::= { gamMvrpConfigInterfaceEntry 2 }

gamMvrpStatus OBJECT IDENTIFIER
    ::= { gamMvrpMibObjects 3 }

gamMvrpStatusInterfaceTable OBJECT-TYPE
    SYNTAX      SEQUENCE OF GAMMvrpStatusInterfaceEntry
    MAX-ACCESS  not-accessible
    STATUS      current
    DESCRIPTION
        "This is the MVRP interface statistics table. The number of interfaces
         is the total number of ports available on the switch/stack. "
    ::= { gamMvrpStatus 1 }

gamMvrpStatusInterfaceEntry OBJECT-TYPE
    SYNTAX      GAMMvrpStatusInterfaceEntry
    MAX-ACCESS  not-accessible
    STATUS      current
    DESCRIPTION
        "Each entry has a counter and a MAC address."
    INDEX       { gamMvrpStatusInterfaceIfIndex }
    ::= { gamMvrpStatusInterfaceTable 1 }

GAMMvrpStatusInterfaceEntry ::= SEQUENCE {
    gamMvrpStatusInterfaceIfIndex              GAMInterfaceIndex,
    gamMvrpStatusInterfaceFailedRegistrations  Counter64,
    gamMvrpStatusInterfaceLastPduOrigin        MacAddress
}

gamMvrpStatusInterfaceIfIndex OBJECT-TYPE
    SYNTAX      GAMInterfaceIndex
    MAX-ACCESS  accessible-for-notify
    STATUS      current
    DESCRIPTION
        "Interface index number."
    ::= { gamMvrpStatusInterfaceEntry 1 }

gamMvrpStatusInterfaceFailedRegistrations OBJECT-TYPE
    SYNTAX      Counter64
    MAX-ACCESS  read-only
    STATUS      current
    DESCRIPTION
        "Number of failed VLAN registrations."
    ::= { gamMvrpStatusInterfaceEntry 2 }

gamMvrpStatusInterfaceLastPduOrigin OBJECT-TYPE
    SYNTAX      MacAddress
    MAX-ACCESS  read-only
    STATUS      current
    DESCRIPTION
        "Source MAC Address of the last MVRPDU received."
    ::= { gamMvrpStatusInterfaceEntry 3 }

gamMvrpMibConformance OBJECT IDENTIFIER
    ::= { gamMvrpMib 2 }

gamMvrpMibCompliances OBJECT IDENTIFIER
    ::= { gamMvrpMibConformance 1 }

gamMvrpMibGroups OBJECT IDENTIFIER
    ::= { gamMvrpMibConformance 2 }

gamMvrpConfigGlobalsInfoGroup OBJECT-GROUP
    OBJECTS     { gamMvrpConfigGlobalsGlobalState,
                  gamMvrpConfigGlobalsManagedVlans0KTo1K,
                  gamMvrpConfigGlobalsManagedVlans1KTo2K,
                  gamMvrpConfigGlobalsManagedVlans2KTo3K,
                  gamMvrpConfigGlobalsManagedVlans3KTo4K }
    STATUS      current
    DESCRIPTION
        "A collection of objects."
    ::= { gamMvrpMibGroups 1 }

gamMvrpConfigInterfaceTableInfoGroup OBJECT-GROUP
    OBJECTS     { gamMvrpConfigInterfaceIfIndex,
                  gamMvrpConfigInterfacePortState }
    STATUS      current
    DESCRIPTION
        "A collection of objects."
    ::= { gamMvrpMibGroups 2 }

gamMvrpStatusInterfaceTableInfoGroup OBJECT-GROUP
    OBJECTS     { gamMvrpStatusInterfaceIfIndex,
                  gamMvrpStatusInterfaceFailedRegistrations,
                  gamMvrpStatusInterfaceLastPduOrigin }
    STATUS      current
    DESCRIPTION
        "A collection of objects."
    ::= { gamMvrpMibGroups 3 }

gamMvrpMibCompliance MODULE-COMPLIANCE
    STATUS      current
    DESCRIPTION
        "The compliance statement for the implementation."

    MODULE      -- this module

    MANDATORY-GROUPS { gamMvrpConfigGlobalsInfoGroup,
                       gamMvrpConfigInterfaceTableInfoGroup,
                       gamMvrpStatusInterfaceTableInfoGroup }

    ::= { gamMvrpMibCompliances 1 }

END
