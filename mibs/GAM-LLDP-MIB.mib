-- *****************************************************************
-- LLDP-MIB:  Positron's GAM private MIB
-- *****************************************************************

GAM-LLDP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    GAMDisplayString FROM GAM-TC
    GAMInteger64 FROM GAM-TC
    GAMInterfaceIndex FROM GAM-TC
    GAMRowEditorState FROM GAM-TC
    GAMUnsigned16 FROM GAM-TC
    GAMUnsigned64 FROM GAM-TC
    GAMUnsigned8 FROM GAM-TC
    Integer32 FROM SNMPv2-SMI
    Unsigned32 FROM SNMPv2-SMI
    TruthValue FROM SNMPv2-TC
    ;

gamLldpMib MODULE-IDENTITY
    LAST-UPDATED "201604070000Z"
    ORGANIZATION
        "Positron Access Solutions Corp."
    CONTACT-INFO
        "Customer Service <info@positronaccess.com>"
    DESCRIPTION
        "This is a private version of the LLDP MIB"
    REVISION    "201604070000Z"
    DESCRIPTION
        "Add SnmpNotificationEna to lldpConfig table"
    REVISION    "201407010000Z"
    DESCRIPTION
        "Initial version"
    ::= { gamMgmt 34 }


GAMLldpAdminState ::= TEXTUAL-CONVENTION
    STATUS      current
    DESCRIPTION
        "This enumerations the admin state."
    SYNTAX      INTEGER { disabled(0), txAndRx(1), txOnly(2),
                          rxOnly(3) }

GAMLldpMedAltitudeType ::= TEXTUAL-CONVENTION
    STATUS      current
    DESCRIPTION
        "This enumerations the altitude type."
    SYNTAX      INTEGER { undefined(0), meters(1), floors(2) }

GAMLldpMedCivicAddressType ::= TEXTUAL-CONVENTION
    STATUS      current
    DESCRIPTION
        "This enumerations the civic address type."
    SYNTAX      INTEGER { state(1), county(2), city(3), district(4),
                          block(5), street(6),
                          leadingStreetDirection(16),
                          trailingStreetSuffix(17), streetSuffix(18),
                          houseNo(19), houseNoSuffix(20),
                          landmark(21), additionalInfo(22), name(23),
                          zipCode(24), building(25), apartment(26),
                          floor(27), roomNumber(28), placeType(29),
                          postalCommunityName(30), poBox(31),
                          additionalCode(32) }

GAMLldpMedDatumType ::= TEXTUAL-CONVENTION
    STATUS      current
    DESCRIPTION
        "This enumerations the datum (geodetic system)."
    SYNTAX      INTEGER { undefined(0), wgs84(1), nad83navd88(2),
                          nad83mllw(3) }

GAMLldpMedDeviceType ::= TEXTUAL-CONVENTION
    STATUS      current
    DESCRIPTION
        "This enumerations the device type that the device shall operate as."
    SYNTAX      INTEGER { connectivity(0), endpoint(1) }

GAMLldpMedRemoteDeviceType ::= TEXTUAL-CONVENTION
    STATUS      current
    DESCRIPTION
        "This enumerations the remote neighbor's device type."
    SYNTAX      INTEGER { notDefined(0), endpointClassI(1),
                          endpointClassII(2), endpointClassIII(3),
                          networkConnectivity(4), reserved(5) }

GAMLldpMedRemoteNetworkPolicyApplicationType ::= TEXTUAL-CONVENTION
    STATUS      current
    DESCRIPTION
        "This enumerations the remote neighbor's network policy's application
         type."
    SYNTAX      INTEGER { voice(1), voiceSignaling(2), guestVoice(3),
                          guestVoiceSignaling(4), softphoneVoice(5),
                          videoConferencing(6), streamingVideo(7),
                          videoSignaling(8) }

gamLldpMibObjects OBJECT IDENTIFIER
    ::= { gamLldpMib 1 }

gamLldpConfig OBJECT IDENTIFIER
    ::= { gamLldpMibObjects 2 }

gamLldpConfigGlobal OBJECT IDENTIFIER
    ::= { gamLldpConfig 1 }

gamLldpConfigGlobalReInitDelay OBJECT-TYPE
    SYNTAX      GAMUnsigned16
    MAX-ACCESS  read-write
    STATUS      current
    DESCRIPTION
        "Set the LLDP tx reinitialization delay in seconds. Valid range 1-10.
         
         When a port is disabled, LLDP is disabled or the switch is rebooted, a
         LLDP shutdown frame is transmitted to the neighboring units, signaling
         that the LLDP information isn't valid anymore.
         
         Tx reinitialization delay controls the amount of seconds between the
         shutdown frame and a new LLDP initialization."
    ::= { gamLldpConfigGlobal 1 }

gamLldpConfigGlobalMsgTxHold OBJECT-TYPE
    SYNTAX      GAMUnsigned16
    MAX-ACCESS  read-write
    STATUS      current
    DESCRIPTION
        "Set the LLDP tx hold times . Valid range 2-10.
         
         Each LLDP frame contains information about how long time the
         information in the LLDP frame shall be considered valid. The LLDP
         information valid period is set to tx hold times multiplied by tx
         interval seconds."
    ::= { gamLldpConfigGlobal 2 }

gamLldpConfigGlobalMsgTxInterval OBJECT-TYPE
    SYNTAX      GAMUnsigned16
    MAX-ACCESS  read-write
    STATUS      current
    DESCRIPTION
        "Set the LLDP tx interval in seconds.
         
         The switch periodically transmits LLDP frames to its neighbors for
         having the network discovery information up-to-date. The interval
         between each LLDP frame is determined by the tx Interval value.
         
         
         
         Valid range 5-32768 seconds."
    ::= { gamLldpConfigGlobal 3 }

gamLldpConfigGlobalTxDelay OBJECT-TYPE
    SYNTAX      GAMUnsigned16
    MAX-ACCESS  read-write
    STATUS      current
    DESCRIPTION
        "Set the LLDP tx delay in seconds. Valid range 1-8192.
         
         If some configuration is changed (e.g. the IP address) a new LLDP frame
         is transmitted, but the time between the LLDP frames will always be at
         least the value of tx delay seconds.
         
         Note: tx Delay cannot be larger than 1/4 of the tx interval."
    ::= { gamLldpConfigGlobal 4 }

gamLldpConfigTable OBJECT-TYPE
    SYNTAX      SEQUENCE OF GAMLldpConfigEntry
    MAX-ACCESS  not-accessible
    STATUS      current
    DESCRIPTION
        "This is a table to configure LLDP configurations for a specific
         interface."
    ::= { gamLldpConfig 2 }

gamLldpConfigEntry OBJECT-TYPE
    SYNTAX      GAMLldpConfigEntry
    MAX-ACCESS  not-accessible
    STATUS      current
    DESCRIPTION
        "Each interface has a set of control parameters"
    INDEX       { gamLldpConfigIfIndex }
    ::= { gamLldpConfigTable 1 }

GAMLldpConfigEntry ::= SEQUENCE {
    gamLldpConfigIfIndex              GAMInterfaceIndex,
    gamLldpConfigAdminState           GAMLldpAdminState,
    gamLldpConfigCdpAware             TruthValue,
    gamLldpConfigOptionalTlvs         GAMUnsigned8,
    gamLldpConfigSnmpNotificationEna  TruthValue
}

gamLldpConfigIfIndex OBJECT-TYPE
    SYNTAX      GAMInterfaceIndex
    MAX-ACCESS  accessible-for-notify
    STATUS      current
    DESCRIPTION
        "Logical interface number index."
    ::= { gamLldpConfigEntry 1 }

gamLldpConfigAdminState OBJECT-TYPE
    SYNTAX      GAMLldpAdminState
    MAX-ACCESS  read-write
    STATUS      current
    DESCRIPTION
        "Sets the LLDP admin state for the interface."
    ::= { gamLldpConfigEntry 3 }

gamLldpConfigCdpAware OBJECT-TYPE
    SYNTAX      TruthValue
    MAX-ACCESS  read-write
    STATUS      current
    DESCRIPTION
        "Enables/disables CDP awareness for the interface.
         
         CDP is Cisco's equivalent to LLDP.
         
         
         
         The CDP operation is restricted to decoding incoming CDP frames (The
         switch doesn't transmit CDP frames). CDP frames are only decoded if
         LLDP on the port is enabled.
         
         
         
         Only CDP TLVs that can be mapped to a corresponding field in the LLDP
         neighbors' table are decoded. All other TLVs are discarded
         (Unrecognized CDP TLVs and discarded CDP frames are not shown in the
         LLDP statistics.).
         
         CDP TLVs are mapped onto LLDP neighbors' table as shown below.
         
         CDP TLV 'Device ID' is mapped to the LLDP 'Chassis ID' field.
         
         CDP TLV 'Address' is mapped to the LLDP 'Management Address' field. The
         CDP address TLV can contain multiple addresses, but only the first
         address is shown in the LLDP neighbors table.
         
         CDP TLV 'Port ID' is mapped to the LLDP 'Port ID' field.
         
         CDP TLV 'Version and Platform' is mapped to the LLDP 'System
         Description' field.
         
         Both the CDP and LLDP support 'system capabilities', but the CDP
         capabilities cover capabilities that are not part of the LLDP. These
         capabilities are shown as 'others' in the LLDP neighbors' table.
         
         
         
         If all ports have CDP awareness disabled the switch forwards CDP frames
         received from neighbor devices. If at least one port has CDP awareness
         enabled all CDP frames are terminated by the switch.
         
         
         
         Note: When CDP awareness on a port is disabled the CDP information
         isn't removed immediately, but gets removed when the hold time is
         exceeded."
    ::= { gamLldpConfigEntry 4 }

gamLldpConfigOptionalTlvs OBJECT-TYPE
    SYNTAX      GAMUnsigned8
    MAX-ACCESS  read-write
    STATUS      current
    DESCRIPTION
        "Enables/Disables the LLDP optional TLVs. Bit mask, where setting the
         bit to 1 means enable transmission of the corresponding TLV.
         
         Bit 0 represents Port Description TLV.
         
         Bit 1 represents System Name TLV.
         
         Bit 2 represents System Description.
         
         Bit 3 represents System Capabilities TLV.
         
         Bit 4 represents Management Address TLV."
    ::= { gamLldpConfigEntry 5 }

gamLldpConfigSnmpNotificationEna OBJECT-TYPE
    SYNTAX      TruthValue
    MAX-ACCESS  read-write
    STATUS      current
    DESCRIPTION
        "Enable/disable of SNMP Trap notification."
    ::= { gamLldpConfigEntry 6 }

gamLldpConfigMed OBJECT IDENTIFIER
    ::= { gamLldpConfig 3 }

gamLldpConfigMedTable OBJECT-TYPE
    SYNTAX      SEQUENCE OF GAMLldpConfigMedEntry
    MAX-ACCESS  not-accessible
    STATUS      current
    DESCRIPTION
        "This is a table to configure LLDP MEDIA configurations for a specific
         interface."
    ::= { gamLldpConfigMed 1 }

gamLldpConfigMedEntry OBJECT-TYPE
    SYNTAX      GAMLldpConfigMedEntry
    MAX-ACCESS  not-accessible
    STATUS      current
    DESCRIPTION
        "Each interface has a set of control parameters"
    INDEX       { gamLldpConfigMedIfIndex }
    ::= { gamLldpConfigMedTable 1 }

GAMLldpConfigMedEntry ::= SEQUENCE {
    gamLldpConfigMedIfIndex       GAMInterfaceIndex,
    gamLldpConfigMedOptionalTlvs  GAMUnsigned8,
    gamLldpConfigMedDeviceType    GAMLldpMedDeviceType
}

gamLldpConfigMedIfIndex OBJECT-TYPE
    SYNTAX      GAMInterfaceIndex
    MAX-ACCESS  accessible-for-notify
    STATUS      current
    DESCRIPTION
        "Logical interface number index."
    ::= { gamLldpConfigMedEntry 1 }

gamLldpConfigMedOptionalTlvs OBJECT-TYPE
    SYNTAX      GAMUnsigned8
    MAX-ACCESS  read-write
    STATUS      current
    DESCRIPTION
        "Enables/Disables the LLDP optional TLVs. Bit mask, where setting the
         bit to 1 means
         
         enable transmission of the corresponding optional TLV.
         
         Bit 0 represents the capabilities TLV.
         
         Bit 1 represents the network Policy TLV.
         
         Bit 2 represents the location TLV.
         
         Bit 3 represents the PoE TLV."
    ::= { gamLldpConfigMedEntry 3 }

gamLldpConfigMedDeviceType OBJECT-TYPE
    SYNTAX      GAMLldpMedDeviceType
    MAX-ACCESS  read-write
    STATUS      current
    DESCRIPTION
        "Setting device type to configure the mode the device shall operate as."
    ::= { gamLldpConfigMedEntry 4 }

gamLldpConfigMedPolicyTable OBJECT-TYPE
    SYNTAX      SEQUENCE OF GAMLldpConfigMedPolicyEntry
    MAX-ACCESS  not-accessible
    STATUS      current
    DESCRIPTION
        "This is a table to configure LLDP MED Policies for the device."
    ::= { gamLldpConfigMed 2 }

gamLldpConfigMedPolicyEntry OBJECT-TYPE
    SYNTAX      GAMLldpConfigMedPolicyEntry
    MAX-ACCESS  not-accessible
    STATUS      current
    DESCRIPTION
        "Network Policy Discovery enables the efficient discovery and diagnosis
         of mismatch issues with the VLAN configuration, along with the
         associated Layer 2 and Layer 3 attributes, which apply for a set of
         specific protocol applications on that port. Improper network policy
         configurations are a very significant issue in VoIP environments that
         frequently result in voice quality degradation or loss of service.
         Policies are only intended for use with applications that have specific
         'real-time' network policy requirements, such as interactive voice
         and/or video services."
    INDEX       { gamLldpConfigMedPolicyLldpmedPolicy }
    ::= { gamLldpConfigMedPolicyTable 1 }

GAMLldpConfigMedPolicyEntry ::= SEQUENCE {
    gamLldpConfigMedPolicyLldpmedPolicy    Integer32,
    gamLldpConfigMedPolicyApplicationType  GAMLldpMedRemoteNetworkPolicyApplicationType,
    gamLldpConfigMedPolicyTagged           TruthValue,
    gamLldpConfigMedPolicyVlanId           GAMUnsigned16,
    gamLldpConfigMedPolicyL2Priority       GAMUnsigned8,
    gamLldpConfigMedPolicyDscp             GAMUnsigned8,
    gamLldpConfigMedPolicyAction           GAMRowEditorState
}

gamLldpConfigMedPolicyLldpmedPolicy OBJECT-TYPE
    SYNTAX      Integer32 (0..31)
    MAX-ACCESS  accessible-for-notify
    STATUS      current
    DESCRIPTION
        "Policy index."
    ::= { gamLldpConfigMedPolicyEntry 1 }

gamLldpConfigMedPolicyApplicationType OBJECT-TYPE
    SYNTAX      GAMLldpMedRemoteNetworkPolicyApplicationType
    MAX-ACCESS  read-write
    STATUS      current
    DESCRIPTION
        "The LLDP policy application type."
    ::= { gamLldpConfigMedPolicyEntry 3 }

gamLldpConfigMedPolicyTagged OBJECT-TYPE
    SYNTAX      TruthValue
    MAX-ACCESS  read-write
    STATUS      current
    DESCRIPTION
        "The LLDP policy tagged flag. Defines if LLDP policy uses tagged VLAN."
    ::= { gamLldpConfigMedPolicyEntry 4 }

gamLldpConfigMedPolicyVlanId OBJECT-TYPE
    SYNTAX      GAMUnsigned16 (1..4095)
    MAX-ACCESS  read-write
    STATUS      current
    DESCRIPTION
        "The LLDP policy VLAN ID. Only valid when policy 'Tagged' is TRUE"
    ::= { gamLldpConfigMedPolicyEntry 5 }

gamLldpConfigMedPolicyL2Priority OBJECT-TYPE
    SYNTAX      GAMUnsigned8 (0..7)
    MAX-ACCESS  read-write
    STATUS      current
    DESCRIPTION
        "The LLDP policy L2 priority."
    ::= { gamLldpConfigMedPolicyEntry 6 }

gamLldpConfigMedPolicyDscp OBJECT-TYPE
    SYNTAX      GAMUnsigned8 (0..63)
    MAX-ACCESS  read-write
    STATUS      current
    DESCRIPTION
        "The LLDP policy DSCP."
    ::= { gamLldpConfigMedPolicyEntry 7 }

gamLldpConfigMedPolicyAction OBJECT-TYPE
    SYNTAX      GAMRowEditorState
    MAX-ACCESS  read-write
    STATUS      current
    DESCRIPTION
        "Action"
    ::= { gamLldpConfigMedPolicyEntry 100 }

gamLldpConfigMedPolicyListTable OBJECT-TYPE
    SYNTAX      SEQUENCE OF GAMLldpConfigMedPolicyListEntry
    MAX-ACCESS  not-accessible
    STATUS      current
    DESCRIPTION
        "Each interface can be mapped to multiple policies. Set to TRUE in order
         to enable the corresponding policy to be transmitted at the interface.
         It is a requirement that the policy is defined."
    ::= { gamLldpConfigMed 3 }

gamLldpConfigMedPolicyListEntry OBJECT-TYPE
    SYNTAX      GAMLldpConfigMedPolicyListEntry
    MAX-ACCESS  not-accessible
    STATUS      current
    DESCRIPTION
        "Each location information has a control parameter"
    INDEX       { gamLldpConfigMedPolicyListIfIndex,
                  gamLldpConfigMedPolicyListLldpmedPolicy }
    ::= { gamLldpConfigMedPolicyListTable 1 }

GAMLldpConfigMedPolicyListEntry ::= SEQUENCE {
    gamLldpConfigMedPolicyListIfIndex              GAMInterfaceIndex,
    gamLldpConfigMedPolicyListLldpmedPolicy        Integer32,
    gamLldpConfigMedPolicyListLldpmedPoliciesList  TruthValue
}

gamLldpConfigMedPolicyListIfIndex OBJECT-TYPE
    SYNTAX      GAMInterfaceIndex
    MAX-ACCESS  accessible-for-notify
    STATUS      current
    DESCRIPTION
        "Logical interface number index."
    ::= { gamLldpConfigMedPolicyListEntry 1 }

gamLldpConfigMedPolicyListLldpmedPolicy OBJECT-TYPE
    SYNTAX      Integer32 (0..31)
    MAX-ACCESS  accessible-for-notify
    STATUS      current
    DESCRIPTION
        "Policy index."
    ::= { gamLldpConfigMedPolicyListEntry 3 }

gamLldpConfigMedPolicyListLldpmedPoliciesList OBJECT-TYPE
    SYNTAX      TruthValue
    MAX-ACCESS  read-write
    STATUS      current
    DESCRIPTION
        "Set to TRUE assign the corresponding policy index to the interface."
    ::= { gamLldpConfigMedPolicyListEntry 4 }

gamLldpConfigMedGlobal OBJECT IDENTIFIER
    ::= { gamLldpConfigMed 4 }

gamLldpConfigMedGlobalFastRepeatCount OBJECT-TYPE
    SYNTAX      GAMUnsigned8 (1..10)
    MAX-ACCESS  read-write
    STATUS      current
    DESCRIPTION
        "Number of times to repeat LLDP frame transmission at fast start
         
         Rapid startup and Emergency Call Service Location Identification
         Discovery of endpoints is a critically important aspect of VoIP systems
         in general. In addition, it is best to advertise only those pieces of
         information which are specifically relevant to particular endpoint
         types (for example only advertise the voice network policy to permitted
         voice-capable devices), both in order to conserve the limited LLDPU
         space and to reduce security and system integrity issues that can come
         with inappropriate knowledge of the network policy.
         
         With this in mind LLDP-MED defines an LLDP-MED Fast Start interaction
         between the protocol and the application layers on top of the protocol,
         in order to achieve these related properties. Initially, a Network
         Connectivity Device will only transmit LLDP TLVs in an LLDPDU. Only
         after an LLDP-MED Endpoint Device is detected, will an LLDP-MED capable
         Network Connectivity Device start to advertise LLDP-MED TLVs in
         outgoing LLDPDUs on the associated port. The LLDP-MED application will
         temporarily speed up the transmission of the LLDPDU to start within a
         second, when a new LLDP-MED neighbor has been detected in order share
         LLDP-MED information as fast as possible to new neighbors.
         
         Because there is a risk of an LLDP frame being lost during transmission
         between neighbors, it is recommended to repeat the fast start
         transmission multiple times to increase the possibility of the
         neighbors receiving the LLDP frame. With fast start repeat count it is
         possible to specify the number of times the fast start transmission
         would be repeated. The recommended value is 4 times, given that 4 LLDP
         frames with a 1 second interval will be transmitted, when an LLDP frame
         with new information is received.
         
         It should be noted that LLDP-MED and the LLDP-MED Fast Start mechanism
         is only intended to run on links between LLDP-MED Network Connectivity
         Devices and Endpoint Devices, and as such does not apply to links
         between LAN infrastructure elements, including Network Connectivity
         Devices, or other types of links."
    ::= { gamLldpConfigMedGlobal 1 }

gamLldpConfigMedGlobalLatitude OBJECT-TYPE
    SYNTAX      GAMInteger64
    MAX-ACCESS  read-write
    STATUS      current
    DESCRIPTION
        "Latitude degrees in 2s-complement as specified in RFC 3825. Positive
         numbers are north of the equator and negative numbers are south of the
         equator."
    ::= { gamLldpConfigMedGlobal 2 }

gamLldpConfigMedGlobalLongitude OBJECT-TYPE
    SYNTAX      GAMInteger64
    MAX-ACCESS  read-write
    STATUS      current
    DESCRIPTION
        "Longitude degrees in 2s-complement as specified in RFC 3825. Positive
         values are East of the prime meridian and negative numbers are West of
         the prime meridian."
    ::= { gamLldpConfigMedGlobal 3 }

gamLldpConfigMedGlobalAltitudeType OBJECT-TYPE
    SYNTAX      GAMLldpMedAltitudeType
    MAX-ACCESS  read-write
    STATUS      current
    DESCRIPTION
        "Setting altitude type
         
         Possible to select between two altitude types (floors or meters).
         Meters are representing meters of altitude defined by the vertical
         datum specified. Floors are representing altitude in a form more
         relevant in buildings which have different floor-to-floor dimensions.
         An altitude = 0.0 is meaningful even outside a building, and represents
         ground level at the given latitude and longitude. Inside a building,
         0.0 represents the floor level associated with ground level at the main
         entrance."
    ::= { gamLldpConfigMedGlobal 4 }

gamLldpConfigMedGlobalAltitude OBJECT-TYPE
    SYNTAX      Integer32
    MAX-ACCESS  read-write
    STATUS      current
    DESCRIPTION
        "Altitude value in 2s-complement as specified in RFC 3825"
    ::= { gamLldpConfigMedGlobal 5 }

gamLldpConfigMedGlobalElinAddr OBJECT-TYPE
    SYNTAX      GAMDisplayString (SIZE(0..25))
    MAX-ACCESS  read-write
    STATUS      current
    DESCRIPTION
        "Emergency Call Service ELIN identifier data format is defined to carry
         the ELIN identifier as used during emergency call setup to a
         traditional CAMA or ISDN trunk-based PSAP. This format consists of a
         numerical digit string, corresponding to the ELIN to be used for
         emergency calling. Maximum number of octets are 25."
    ::= { gamLldpConfigMedGlobal 6 }

gamLldpConfigMedGlobalDatum OBJECT-TYPE
    SYNTAX      GAMLldpMedDatumType
    MAX-ACCESS  read-write
    STATUS      current
    DESCRIPTION
        "Setting datum to configure the datum (geodetic system) to use.
         
         The Map Datum is used for the coordinates given in these options:
         
         WGS84: (Geographical 3D) - World Geodesic System 1984, CRS Code 4327,
         Prime Meridian Name: Greenwich.
         
         NAD83/NAVD88: North American Datum 1983, CRS Code 4269, Prime Meridian
         Name: Greenwich;The associated vertical datum is the North American
         Vertical Datum of 1988 (NAVD88).This datum pair is to be used when
         referencing locations on land, not near tidal water(which would use
         Datum = NAD83/MLLW).
         
         NAD83/MLLW: North American Datum 1983, CRS Code 4269, Prime Meridian
         Name: Greenwich; The associated vertical datum is Mean Lower Low Water
         (MLLW). This datum pair is to be used when referencing locations on
         water/sea/ocean."
    ::= { gamLldpConfigMedGlobal 7 }

gamLldpConfigMedGlobalCountryCode OBJECT-TYPE
    SYNTAX      GAMDisplayString (SIZE(0..2))
    MAX-ACCESS  read-write
    STATUS      current
    DESCRIPTION
        "The two-letter ISO 3166 country code in capital ASCII letters -
         Example: DK, DE or US."
    ::= { gamLldpConfigMedGlobal 8 }

gamLldpConfigMedLocationInformationTable OBJECT-TYPE
    SYNTAX      SEQUENCE OF GAMLldpConfigMedLocationInformationEntry
    MAX-ACCESS  not-accessible
    STATUS      current
    DESCRIPTION
        "The civic address location information. Each civic address can contain
         up to 250 characters, but the total amount of characters for the
         combined civic address locations must not exceed 250 bytes. Note: If an
         civic address location is non-empty it uses the amount of characters
         plus addition two characters. This is described in TIA1057, Section
         10.2.4.3.2."
    ::= { gamLldpConfigMed 5 }

gamLldpConfigMedLocationInformationEntry OBJECT-TYPE
    SYNTAX      GAMLldpConfigMedLocationInformationEntry
    MAX-ACCESS  not-accessible
    STATUS      current
    DESCRIPTION
        "Each civic address type as defined in TIA1057, Section 3.4 in Annex B"
    INDEX       { gamLldpConfigMedLocationInformationLldpmedIndex }
    ::= { gamLldpConfigMedLocationInformationTable 1 }

GAMLldpConfigMedLocationInformationEntry ::= SEQUENCE {
    gamLldpConfigMedLocationInformationLldpmedIndex  GAMLldpMedCivicAddressType,
    gamLldpConfigMedLocationInformationCivicAddress  GAMDisplayString
}

gamLldpConfigMedLocationInformationLldpmedIndex OBJECT-TYPE
    SYNTAX      GAMLldpMedCivicAddressType
    MAX-ACCESS  accessible-for-notify
    STATUS      current
    DESCRIPTION
        "Civic address type.
         
         1 - State/National subdivisions
         
         2 - County, parish, gun (JP), district (IN)
         
         3 - City, township
         
         4 - City division, borough, city district, ward, chou (JP)
         
         5 - Neighborhood, block
         
         6 - Street
         
         16 - Leading street direction
         
         17 - Trailing street direction
         
         18 - Street suffix
         
         19 - House number
         
         20 - House number suffix
         
         21 - Landmark or vanity address
         
         22 - Additional location information
         
         23 - Name
         
         24 - Postal/zip code
         
         25 - Building
         
         26 - Unit
         
         27 - Floor
         
         28 - Room
         
         29 - Place type
         
         30 - Postal
         
         31 - Post office
         
         32 - Additional code"
    ::= { gamLldpConfigMedLocationInformationEntry 2 }

gamLldpConfigMedLocationInformationCivicAddress OBJECT-TYPE
    SYNTAX      GAMDisplayString (SIZE(0..250))
    MAX-ACCESS  read-write
    STATUS      current
    DESCRIPTION
        "Civic address"
    ::= { gamLldpConfigMedLocationInformationEntry 3 }

gamLldpConfigMedPolicyRowEditor OBJECT IDENTIFIER
    ::= { gamLldpConfigMed 6 }

gamLldpConfigMedPolicyRowEditorLldpmedPolicy OBJECT-TYPE
    SYNTAX      Integer32 (0..31)
    MAX-ACCESS  read-write
    STATUS      current
    DESCRIPTION
        "Policy index."
    ::= { gamLldpConfigMedPolicyRowEditor 1 }

gamLldpConfigMedPolicyRowEditorApplicationType OBJECT-TYPE
    SYNTAX      GAMLldpMedRemoteNetworkPolicyApplicationType
    MAX-ACCESS  read-write
    STATUS      current
    DESCRIPTION
        "The LLDP policy application type."
    ::= { gamLldpConfigMedPolicyRowEditor 3 }

gamLldpConfigMedPolicyRowEditorTagged OBJECT-TYPE
    SYNTAX      TruthValue
    MAX-ACCESS  read-write
    STATUS      current
    DESCRIPTION
        "The LLDP policy tagged flag. Defines if LLDP policy uses tagged VLAN."
    ::= { gamLldpConfigMedPolicyRowEditor 4 }

gamLldpConfigMedPolicyRowEditorVlanId OBJECT-TYPE
    SYNTAX      GAMUnsigned16 (1..4095)
    MAX-ACCESS  read-write
    STATUS      current
    DESCRIPTION
        "The LLDP policy VLAN ID. Only valid when policy 'Tagged' is TRUE"
    ::= { gamLldpConfigMedPolicyRowEditor 5 }

gamLldpConfigMedPolicyRowEditorL2Priority OBJECT-TYPE
    SYNTAX      GAMUnsigned8 (0..7)
    MAX-ACCESS  read-write
    STATUS      current
    DESCRIPTION
        "The LLDP policy L2 priority."
    ::= { gamLldpConfigMedPolicyRowEditor 6 }

gamLldpConfigMedPolicyRowEditorDscp OBJECT-TYPE
    SYNTAX      GAMUnsigned8 (0..63)
    MAX-ACCESS  read-write
    STATUS      current
    DESCRIPTION
        "The LLDP policy DSCP."
    ::= { gamLldpConfigMedPolicyRowEditor 7 }

gamLldpConfigMedPolicyRowEditorAction OBJECT-TYPE
    SYNTAX      GAMRowEditorState
    MAX-ACCESS  read-write
    STATUS      current
    DESCRIPTION
        "Action"
    ::= { gamLldpConfigMedPolicyRowEditor 100 }

gamLldpStatus OBJECT IDENTIFIER
    ::= { gamLldpMibObjects 3 }

gamLldpStatusStatistics OBJECT IDENTIFIER
    ::= { gamLldpStatus 1 }

gamLldpStatusStatisticsGlobalCounters OBJECT IDENTIFIER
    ::= { gamLldpStatusStatistics 1 }

gamLldpStatusStatisticsGlobalCountersTableInserts OBJECT-TYPE
    SYNTAX      Unsigned32
    MAX-ACCESS  read-only
    STATUS      current
    DESCRIPTION
        "Shows the number of new entries added since switch reboot."
    ::= { gamLldpStatusStatisticsGlobalCounters 1 }

gamLldpStatusStatisticsGlobalCountersTableDeletes OBJECT-TYPE
    SYNTAX      Unsigned32
    MAX-ACCESS  read-only
    STATUS      current
    DESCRIPTION
        "Shows the number of new entries deleted since switch reboot."
    ::= { gamLldpStatusStatisticsGlobalCounters 2 }

gamLldpStatusStatisticsGlobalCountersTableDrops OBJECT-TYPE
    SYNTAX      Unsigned32
    MAX-ACCESS  read-only
    STATUS      current
    DESCRIPTION
        "Shows the number of LLDP frames dropped due to the entry table being
         full."
    ::= { gamLldpStatusStatisticsGlobalCounters 3 }

gamLldpStatusStatisticsGlobalCountersTableAgeOuts OBJECT-TYPE
    SYNTAX      Unsigned32
    MAX-ACCESS  read-only
    STATUS      current
    DESCRIPTION
        "Shows the number of entries deleted due to Time-To-Live expiring."
    ::= { gamLldpStatusStatisticsGlobalCounters 4 }

gamLldpStatusStatisticsGlobalCountersLastChangeTime OBJECT-TYPE
    SYNTAX      GAMUnsigned64
    MAX-ACCESS  read-only
    STATUS      current
    DESCRIPTION
        "Shows the time when the last entry was last deleted or added. It also
         shows the time elapsed since the last change was detected."
    ::= { gamLldpStatusStatisticsGlobalCounters 5 }

gamLldpStatusStatisticsTable OBJECT-TYPE
    SYNTAX      SEQUENCE OF GAMLldpStatusStatisticsEntry
    MAX-ACCESS  not-accessible
    STATUS      current
    DESCRIPTION
        "This table represents the LLDP interface counters"
    ::= { gamLldpStatusStatistics 2 }

gamLldpStatusStatisticsEntry OBJECT-TYPE
    SYNTAX      GAMLldpStatusStatisticsEntry
    MAX-ACCESS  not-accessible
    STATUS      current
    DESCRIPTION
        "Each port interface has a set of statistics counters"
    INDEX       { gamLldpStatusStatisticsIfIndex }
    ::= { gamLldpStatusStatisticsTable 1 }

GAMLldpStatusStatisticsEntry ::= SEQUENCE {
    gamLldpStatusStatisticsIfIndex           GAMInterfaceIndex,
    gamLldpStatusStatisticsTxTotal           Unsigned32,
    gamLldpStatusStatisticsRxTotal           Unsigned32,
    gamLldpStatusStatisticsRxError           Unsigned32,
    gamLldpStatusStatisticsRxDiscarded       Unsigned32,
    gamLldpStatusStatisticsTLVsDiscarded     Unsigned32,
    gamLldpStatusStatisticsTLVsUnrecognized  Unsigned32,
    gamLldpStatusStatisticsTLVsOrgDiscarded  Unsigned32,
    gamLldpStatusStatisticsAgeOuts           Unsigned32
}

gamLldpStatusStatisticsIfIndex OBJECT-TYPE
    SYNTAX      GAMInterfaceIndex
    MAX-ACCESS  accessible-for-notify
    STATUS      current
    DESCRIPTION
        "Logical interface number index."
    ::= { gamLldpStatusStatisticsEntry 1 }

gamLldpStatusStatisticsTxTotal OBJECT-TYPE
    SYNTAX      Unsigned32
    MAX-ACCESS  read-only
    STATUS      current
    DESCRIPTION
        "Shows the number of LLDP frames transmitted."
    ::= { gamLldpStatusStatisticsEntry 2 }

gamLldpStatusStatisticsRxTotal OBJECT-TYPE
    SYNTAX      Unsigned32
    MAX-ACCESS  read-only
    STATUS      current
    DESCRIPTION
        "Shows the number of LLDP frames received."
    ::= { gamLldpStatusStatisticsEntry 3 }

gamLldpStatusStatisticsRxError OBJECT-TYPE
    SYNTAX      Unsigned32
    MAX-ACCESS  read-only
    STATUS      current
    DESCRIPTION
        "Shows the number of received LLDP frames containing some kind of error."
    ::= { gamLldpStatusStatisticsEntry 4 }

gamLldpStatusStatisticsRxDiscarded OBJECT-TYPE
    SYNTAX      Unsigned32
    MAX-ACCESS  read-only
    STATUS      current
    DESCRIPTION
        "Show the number of LLDP frames discarded. If a LLDP frame is received
         at an interface, and the switch's internal table has run full, the LLDP
         frame is counted and discarded. This situation is known as 'Too Many
         Neighbors' in the LLDP standard. LLDP frames require a new entry in the
         table when the Chassis ID or Remote Port ID is not already contained
         within the table. Entries are removed from the table when a given
         interface's link is down, an LLDP shutdown frame is received, or when
         the entry ages out."
    ::= { gamLldpStatusStatisticsEntry 5 }

gamLldpStatusStatisticsTLVsDiscarded OBJECT-TYPE
    SYNTAX      Unsigned32
    MAX-ACCESS  read-only
    STATUS      current
    DESCRIPTION
        "Shows the number of TLVs discarded. Each LLDP frame can contain
         multiple pieces of information, known as TLVs (TLV is short for 'Type
         Length Value'). If a TLV is malformed, it is counted and discarded."
    ::= { gamLldpStatusStatisticsEntry 6 }

gamLldpStatusStatisticsTLVsUnrecognized OBJECT-TYPE
    SYNTAX      Unsigned32
    MAX-ACCESS  read-only
    STATUS      current
    DESCRIPTION
        "Shows the number of well-formed TLVs, but with an unknown type value."
    ::= { gamLldpStatusStatisticsEntry 7 }

gamLldpStatusStatisticsTLVsOrgDiscarded OBJECT-TYPE
    SYNTAX      Unsigned32
    MAX-ACCESS  read-only
    STATUS      current
    DESCRIPTION
        "Shows the number of well-formed TLVs, but with an organizationally TLV
         which is not supported."
    ::= { gamLldpStatusStatisticsEntry 8 }

gamLldpStatusStatisticsAgeOuts OBJECT-TYPE
    SYNTAX      Unsigned32
    MAX-ACCESS  read-only
    STATUS      current
    DESCRIPTION
        "Show the number of age-outs. Each frame contains information about how
         long time the LLDP information is valid (age-out time). If no new LLDP
         frame is received within the age out time, the information is removed,
         and the counter is incremented."
    ::= { gamLldpStatusStatisticsEntry 9 }

gamLldpStatusNeighborsInformationTable OBJECT-TYPE
    SYNTAX      SEQUENCE OF GAMLldpStatusNeighborsInformationEntry
    MAX-ACCESS  not-accessible
    STATUS      current
    DESCRIPTION
        "This is a table to show the LLDP neighbors information for a specific
         interface."
    ::= { gamLldpStatus 2 }

gamLldpStatusNeighborsInformationEntry OBJECT-TYPE
    SYNTAX      GAMLldpStatusNeighborsInformationEntry
    MAX-ACCESS  not-accessible
    STATUS      current
    DESCRIPTION
        "Each interface has a set of neighbors information"
    INDEX       { gamLldpStatusNeighborsInformationIfIndex,
                  gamLldpStatusNeighborsInformationLldpmedIndex }
    ::= { gamLldpStatusNeighborsInformationTable 1 }

GAMLldpStatusNeighborsInformationEntry ::= SEQUENCE {
    gamLldpStatusNeighborsInformationIfIndex                   GAMInterfaceIndex,
    gamLldpStatusNeighborsInformationLldpmedIndex              Integer32,
    gamLldpStatusNeighborsInformationChassisId                 GAMDisplayString,
    gamLldpStatusNeighborsInformationPortId                    GAMDisplayString,
    gamLldpStatusNeighborsInformationPortDescription           GAMDisplayString,
    gamLldpStatusNeighborsInformationSystemName                GAMDisplayString,
    gamLldpStatusNeighborsInformationSystemDescription         GAMDisplayString,
    gamLldpStatusNeighborsInformationSystemCapabilities        GAMUnsigned16,
    gamLldpStatusNeighborsInformationSystemCapabilitiesEnable  GAMUnsigned16
}

gamLldpStatusNeighborsInformationIfIndex OBJECT-TYPE
    SYNTAX      GAMInterfaceIndex
    MAX-ACCESS  accessible-for-notify
    STATUS      current
    DESCRIPTION
        "Logical interface number index."
    ::= { gamLldpStatusNeighborsInformationEntry 1 }

gamLldpStatusNeighborsInformationLldpmedIndex OBJECT-TYPE
    SYNTAX      Integer32 (0..192)
    MAX-ACCESS  accessible-for-notify
    STATUS      current
    DESCRIPTION
        "Neighbor information table entry index."
    ::= { gamLldpStatusNeighborsInformationEntry 2 }

gamLldpStatusNeighborsInformationChassisId OBJECT-TYPE
    SYNTAX      GAMDisplayString (SIZE(0..254))
    MAX-ACCESS  read-only
    STATUS      current
    DESCRIPTION
        "Shows the LLDP neighbor's chassis Id."
    ::= { gamLldpStatusNeighborsInformationEntry 4 }

gamLldpStatusNeighborsInformationPortId OBJECT-TYPE
    SYNTAX      GAMDisplayString (SIZE(0..254))
    MAX-ACCESS  read-only
    STATUS      current
    DESCRIPTION
        "Shows the LLDP neighbor's port id."
    ::= { gamLldpStatusNeighborsInformationEntry 5 }

gamLldpStatusNeighborsInformationPortDescription OBJECT-TYPE
    SYNTAX      GAMDisplayString (SIZE(0..254))
    MAX-ACCESS  read-only
    STATUS      current
    DESCRIPTION
        "Shows the LLDP neighbor's port description."
    ::= { gamLldpStatusNeighborsInformationEntry 6 }

gamLldpStatusNeighborsInformationSystemName OBJECT-TYPE
    SYNTAX      GAMDisplayString (SIZE(0..254))
    MAX-ACCESS  read-only
    STATUS      current
    DESCRIPTION
        "Shows the LLDP neighbor's system name."
    ::= { gamLldpStatusNeighborsInformationEntry 7 }

gamLldpStatusNeighborsInformationSystemDescription OBJECT-TYPE
    SYNTAX      GAMDisplayString (SIZE(0..254))
    MAX-ACCESS  read-only
    STATUS      current
    DESCRIPTION
        "Shows the LLDP neighbor's system description."
    ::= { gamLldpStatusNeighborsInformationEntry 8 }

gamLldpStatusNeighborsInformationSystemCapabilities OBJECT-TYPE
    SYNTAX      GAMUnsigned16
    MAX-ACCESS  read-only
    STATUS      current
    DESCRIPTION
        "Shows the LLDP neighbor's system capabilities as bit mask.
         
         If the bit is set, it means that the functionality is supported by the
         neighbor system.
         
         Bit 0 represents Other.
         
         Bit 1 represents Repeater.
         
         Bit 2 represents Bridge.
         
         Bit 3 represents WLAN Access Point.
         
         Bit 4 represents Router.
         
         Bit 5 represents Telephone.
         
         Bit 6 represents DOCSIS cable device.
         
         Bit 7 represents Station Only.
         
         Bit 8 represents Reserved."
    ::= { gamLldpStatusNeighborsInformationEntry 9 }

gamLldpStatusNeighborsInformationSystemCapabilitiesEnable OBJECT-TYPE
    SYNTAX      GAMUnsigned16
    MAX-ACCESS  read-only
    STATUS      current
    DESCRIPTION
        "Shows the LLDP neighbor's system capabilities which is enabled.
         
         If the bit is set, it means that the functionality is currently enabled
         at the neighbor system.
         
         Bit 0 represents Other.
         
         Bit 1 represents Repeater.
         
         Bit 2 represents Bridge.
         
         Bit 3 represents WLAN Access Point.
         
         Bit 4 represents Router.
         
         Bit 5 represents Telephone.
         
         Bit 6 represents DOCSIS cable device.
         
         Bit 7 represents Station Only.
         
         Bit 8 represents Reserved."
    ::= { gamLldpStatusNeighborsInformationEntry 10 }

gamLldpStatusNeighborsMgmtInformationTable OBJECT-TYPE
    SYNTAX      SEQUENCE OF GAMLldpStatusNeighborsMgmtInformationEntry
    MAX-ACCESS  not-accessible
    STATUS      current
    DESCRIPTION
        "This is a table to show the LLDP neighbors information for a specific
         interface."
    ::= { gamLldpStatus 3 }

gamLldpStatusNeighborsMgmtInformationEntry OBJECT-TYPE
    SYNTAX      GAMLldpStatusNeighborsMgmtInformationEntry
    MAX-ACCESS  not-accessible
    STATUS      current
    DESCRIPTION
        "Each interface has a set of neighbors information"
    INDEX       { gamLldpStatusNeighborsMgmtInformationIfIndex,
                  gamLldpStatusNeighborsMgmtInformationLldpmedIndex,
                  gamLldpStatusNeighborsMgmtInformationLldpManagement }
    ::= { gamLldpStatusNeighborsMgmtInformationTable 1 }

GAMLldpStatusNeighborsMgmtInformationEntry ::= SEQUENCE {
    gamLldpStatusNeighborsMgmtInformationIfIndex                     GAMInterfaceIndex,
    gamLldpStatusNeighborsMgmtInformationLldpmedIndex                Integer32,
    gamLldpStatusNeighborsMgmtInformationLldpManagement              Integer32,
    gamLldpStatusNeighborsMgmtInformationSystemMgmAddressSubtype     GAMUnsigned8,
    gamLldpStatusNeighborsMgmtInformationSystemMgmtAddress           GAMDisplayString,
    gamLldpStatusNeighborsMgmtInformationSystemMgmtInterfaceSubtype  Integer32,
    gamLldpStatusNeighborsMgmtInformationSystemMgmtInterface         Integer32,
    gamLldpStatusNeighborsMgmtInformationSystemMgmtOid               OBJECT IDENTIFIER
}

gamLldpStatusNeighborsMgmtInformationIfIndex OBJECT-TYPE
    SYNTAX      GAMInterfaceIndex
    MAX-ACCESS  accessible-for-notify
    STATUS      current
    DESCRIPTION
        "Logical interface number index."
    ::= { gamLldpStatusNeighborsMgmtInformationEntry 1 }

gamLldpStatusNeighborsMgmtInformationLldpmedIndex OBJECT-TYPE
    SYNTAX      Integer32 (0..192)
    MAX-ACCESS  accessible-for-notify
    STATUS      current
    DESCRIPTION
        "Neighbor information table entry index."
    ::= { gamLldpStatusNeighborsMgmtInformationEntry 2 }

gamLldpStatusNeighborsMgmtInformationLldpManagement OBJECT-TYPE
    SYNTAX      Integer32 (0..1)
    MAX-ACCESS  accessible-for-notify
    STATUS      current
    DESCRIPTION
        "Neighbor management information table entry index."
    ::= { gamLldpStatusNeighborsMgmtInformationEntry 4 }

gamLldpStatusNeighborsMgmtInformationSystemMgmAddressSubtype OBJECT-TYPE
    SYNTAX      GAMUnsigned8
    MAX-ACCESS  read-only
    STATUS      current
    DESCRIPTION
        "LLDP neighbor's management address subtype , section 9.5.9.3
         IEEE802.1AB-2005."
    ::= { gamLldpStatusNeighborsMgmtInformationEntry 5 }

gamLldpStatusNeighborsMgmtInformationSystemMgmtAddress OBJECT-TYPE
    SYNTAX      GAMDisplayString (SIZE(0..31))
    MAX-ACCESS  read-only
    STATUS      current
    DESCRIPTION
        "LLDP neighbor's management address string, section 9.5.9.4
         IEEE802.1AB-2005."
    ::= { gamLldpStatusNeighborsMgmtInformationEntry 6 }

gamLldpStatusNeighborsMgmtInformationSystemMgmtInterfaceSubtype OBJECT-TYPE
    SYNTAX      Integer32
    MAX-ACCESS  read-only
    STATUS      current
    DESCRIPTION
        "Interface numbering subtype, section 9.5.9.5 IEEE802.1AB-2005."
    ::= { gamLldpStatusNeighborsMgmtInformationEntry 7 }

gamLldpStatusNeighborsMgmtInformationSystemMgmtInterface OBJECT-TYPE
    SYNTAX      Integer32
    MAX-ACCESS  read-only
    STATUS      current
    DESCRIPTION
        "Interface number, section 9.5.9.6 IEEE802.1AB-2005."
    ::= { gamLldpStatusNeighborsMgmtInformationEntry 8 }

gamLldpStatusNeighborsMgmtInformationSystemMgmtOid OBJECT-TYPE
    SYNTAX      OBJECT IDENTIFIER
    MAX-ACCESS  read-only
    STATUS      current
    DESCRIPTION
        "Object identifier, section 9.5.9.8 IEEE802.1AB-2005."
    ::= { gamLldpStatusNeighborsMgmtInformationEntry 9 }

gamLldpStatusPreemptInformationTable OBJECT-TYPE
    SYNTAX      SEQUENCE OF GAMLldpStatusPreemptInformationEntry
    MAX-ACCESS  not-accessible
    STATUS      current
    DESCRIPTION
        "This is a table to show the LLDP Frame Preemption information for a
         specific interface."
    ::= { gamLldpStatus 4 }

gamLldpStatusPreemptInformationEntry OBJECT-TYPE
    SYNTAX      GAMLldpStatusPreemptInformationEntry
    MAX-ACCESS  not-accessible
    STATUS      current
    DESCRIPTION
        "Each interface has a Frame preemption information"
    INDEX       { gamLldpStatusPreemptInformationIfIndex,
                  gamLldpStatusPreemptInformationLldpmedIndex,
                  gamLldpStatusPreemptInformationLldpManagement }
    ::= { gamLldpStatusPreemptInformationTable 1 }

GAMLldpStatusPreemptInformationEntry ::= SEQUENCE {
    gamLldpStatusPreemptInformationIfIndex                   GAMInterfaceIndex,
    gamLldpStatusPreemptInformationLldpmedIndex              Integer32,
    gamLldpStatusPreemptInformationLldpManagement            Integer32,
    gamLldpStatusPreemptInformationLocPreemptSupported       TruthValue,
    gamLldpStatusPreemptInformationLocPreemptEnabled         TruthValue,
    gamLldpStatusPreemptInformationLocPreemptActive          TruthValue,
    gamLldpStatusPreemptInformationLocAddFragSize            GAMUnsigned8,
    gamLldpStatusPreemptInformationRemFramePreemptSupported  TruthValue,
    gamLldpStatusPreemptInformationRemFramePreemptEnabled    TruthValue,
    gamLldpStatusPreemptInformationRemFramePreemptActive     TruthValue,
    gamLldpStatusPreemptInformationRemFrameAddFragSize       GAMUnsigned8
}

gamLldpStatusPreemptInformationIfIndex OBJECT-TYPE
    SYNTAX      GAMInterfaceIndex
    MAX-ACCESS  accessible-for-notify
    STATUS      current
    DESCRIPTION
        "Logical interface number index."
    ::= { gamLldpStatusPreemptInformationEntry 1 }

gamLldpStatusPreemptInformationLldpmedIndex OBJECT-TYPE
    SYNTAX      Integer32 (0..192)
    MAX-ACCESS  accessible-for-notify
    STATUS      current
    DESCRIPTION
        "Neighbor information table entry index."
    ::= { gamLldpStatusPreemptInformationEntry 2 }

gamLldpStatusPreemptInformationLldpManagement OBJECT-TYPE
    SYNTAX      Integer32 (0..1)
    MAX-ACCESS  accessible-for-notify
    STATUS      current
    DESCRIPTION
        "Neighbor management information table entry index."
    ::= { gamLldpStatusPreemptInformationEntry 4 }

gamLldpStatusPreemptInformationLocPreemptSupported OBJECT-TYPE
    SYNTAX      TruthValue
    MAX-ACCESS  read-only
    STATUS      current
    DESCRIPTION
        "The value of the 802.3br LocPreemptSupported parameter for the port.
         The value is TRUE when preemption is supported on the port, and FALSE
         otherwise."
    ::= { gamLldpStatusPreemptInformationEntry 5 }

gamLldpStatusPreemptInformationLocPreemptEnabled OBJECT-TYPE
    SYNTAX      TruthValue
    MAX-ACCESS  read-only
    STATUS      current
    DESCRIPTION
        "The value of the 802.3br LocPreemptEnabled parameter for the port. The
         value is TRUE when preemption is enabled on the port, and FALSE
         otherwise."
    ::= { gamLldpStatusPreemptInformationEntry 6 }

gamLldpStatusPreemptInformationLocPreemptActive OBJECT-TYPE
    SYNTAX      TruthValue
    MAX-ACCESS  read-only
    STATUS      current
    DESCRIPTION
        "The value of the 802.3br LocPreemptActive parameter for the port. The
         value is TRUE when preemption is operationally active on the port, and
         FALSE otherwise."
    ::= { gamLldpStatusPreemptInformationEntry 7 }

gamLldpStatusPreemptInformationLocAddFragSize OBJECT-TYPE
    SYNTAX      GAMUnsigned8
    MAX-ACCESS  read-only
    STATUS      current
    DESCRIPTION
        "The value of the 802.3br LocAddFragSize parameter for the port. The
         minimum size of non-final fragments supported by the receiver on the
         local port. This value is expressed in units of 64 octets of additional
         fragment length. The minimum non-final fragment size is:
         (LocAddFragSize + 1) * 64 octets"
    ::= { gamLldpStatusPreemptInformationEntry 8 }

gamLldpStatusPreemptInformationRemFramePreemptSupported OBJECT-TYPE
    SYNTAX      TruthValue
    MAX-ACCESS  read-only
    STATUS      current
    DESCRIPTION
        "The value of the 802.3br RemPreemptSupported parameter for the port.
         The value is TRUE when preemption is supported on the port, and FALSE
         otherwise."
    ::= { gamLldpStatusPreemptInformationEntry 9 }

gamLldpStatusPreemptInformationRemFramePreemptEnabled OBJECT-TYPE
    SYNTAX      TruthValue
    MAX-ACCESS  read-only
    STATUS      current
    DESCRIPTION
        "The value of the 802.3br RemPreemptEnabled parameter for the port. The
         value is TRUE when preemption is enabled on the port, and FALSE
         otherwise."
    ::= { gamLldpStatusPreemptInformationEntry 10 }

gamLldpStatusPreemptInformationRemFramePreemptActive OBJECT-TYPE
    SYNTAX      TruthValue
    MAX-ACCESS  read-only
    STATUS      current
    DESCRIPTION
        "The value of the 802.3br RemPreemptActive parameter for the port. The
         value is TRUE when preemption is operationally active on the port, and
         FALSE otherwise."
    ::= { gamLldpStatusPreemptInformationEntry 11 }

gamLldpStatusPreemptInformationRemFrameAddFragSize OBJECT-TYPE
    SYNTAX      GAMUnsigned8
    MAX-ACCESS  read-only
    STATUS      current
    DESCRIPTION
        "The value of the 802.3br RemAddFragSize parameter for the port. The
         minimum size of non-final fragments supported by the receiver on the
         local port. This value is expressed in units of 64 octets of additional
         fragment length. The minimum non-final fragment size is:
         (LocAddFragSize + 1) * 64 octets"
    ::= { gamLldpStatusPreemptInformationEntry 12 }

gamLldpStatusMed OBJECT IDENTIFIER
    ::= { gamLldpStatus 5 }

gamLldpStatusMedRemoteDeviceInfoTable OBJECT-TYPE
    SYNTAX      SEQUENCE OF GAMLldpStatusMedRemoteDeviceInfoEntry
    MAX-ACCESS  not-accessible
    STATUS      current
    DESCRIPTION
        "This is a table to show the LLDP neighbors information for a specific
         interface."
    ::= { gamLldpStatusMed 1 }

gamLldpStatusMedRemoteDeviceInfoEntry OBJECT-TYPE
    SYNTAX      GAMLldpStatusMedRemoteDeviceInfoEntry
    MAX-ACCESS  not-accessible
    STATUS      current
    DESCRIPTION
        "Each interface has a set of neighbors information"
    INDEX       { gamLldpStatusMedRemoteDeviceInfoIfIndex,
                  gamLldpStatusMedRemoteDeviceInfoLldpmedIndex }
    ::= { gamLldpStatusMedRemoteDeviceInfoTable 1 }

GAMLldpStatusMedRemoteDeviceInfoEntry ::= SEQUENCE {
    gamLldpStatusMedRemoteDeviceInfoIfIndex              GAMInterfaceIndex,
    gamLldpStatusMedRemoteDeviceInfoLldpmedIndex         Integer32,
    gamLldpStatusMedRemoteDeviceInfoCapabilities         GAMUnsigned16,
    gamLldpStatusMedRemoteDeviceInfoCapabilitiesEnabled  GAMUnsigned16,
    gamLldpStatusMedRemoteDeviceInfoLatitude             GAMInteger64,
    gamLldpStatusMedRemoteDeviceInfoLongitude            GAMInteger64,
    gamLldpStatusMedRemoteDeviceInfoAltitudeType         GAMLldpMedAltitudeType,
    gamLldpStatusMedRemoteDeviceInfoAltitude             Integer32,
    gamLldpStatusMedRemoteDeviceInfoDatum                GAMLldpMedDatumType,
    gamLldpStatusMedRemoteDeviceInfoElinaddr             GAMDisplayString,
    gamLldpStatusMedRemoteDeviceInfoDeviceType           GAMLldpMedRemoteDeviceType,
    gamLldpStatusMedRemoteDeviceInfoHwRev                GAMDisplayString,
    gamLldpStatusMedRemoteDeviceInfoFwRev                GAMDisplayString,
    gamLldpStatusMedRemoteDeviceInfoSwRev                GAMDisplayString,
    gamLldpStatusMedRemoteDeviceInfoSerialNo             GAMDisplayString,
    gamLldpStatusMedRemoteDeviceInfoManufacturerName     GAMDisplayString,
    gamLldpStatusMedRemoteDeviceInfoModelName            GAMDisplayString,
    gamLldpStatusMedRemoteDeviceInfoAssetId              GAMDisplayString,
    gamLldpStatusMedRemoteDeviceInfoEeeRxTwSys           GAMUnsigned16,
    gamLldpStatusMedRemoteDeviceInfoEeeTxTwSys           GAMUnsigned16,
    gamLldpStatusMedRemoteDeviceInfoEeeFbTwSys           GAMUnsigned16,
    gamLldpStatusMedRemoteDeviceInfoEeeTxTwSysEcho       GAMUnsigned16,
    gamLldpStatusMedRemoteDeviceInfoEeeRxTwSysEcho       GAMUnsigned16
}

gamLldpStatusMedRemoteDeviceInfoIfIndex OBJECT-TYPE
    SYNTAX      GAMInterfaceIndex
    MAX-ACCESS  accessible-for-notify
    STATUS      current
    DESCRIPTION
        "Logical interface number index."
    ::= { gamLldpStatusMedRemoteDeviceInfoEntry 1 }

gamLldpStatusMedRemoteDeviceInfoLldpmedIndex OBJECT-TYPE
    SYNTAX      Integer32 (0..192)
    MAX-ACCESS  accessible-for-notify
    STATUS      current
    DESCRIPTION
        "Neighbor information table entry index."
    ::= { gamLldpStatusMedRemoteDeviceInfoEntry 2 }

gamLldpStatusMedRemoteDeviceInfoCapabilities OBJECT-TYPE
    SYNTAX      GAMUnsigned16
    MAX-ACCESS  read-only
    STATUS      current
    DESCRIPTION
        "LLDP neighbor's capabilities bit mask.
         
         Bit 0 represents LLDP-MED capabilities.
         
         Bit 1 represents Network Policy.
         
         Bit 2 represents Location Identification.
         
         Bit 3 represents Extended Power via MDI - PSE.
         
         Bit 4 represents Extended Power via MDI - PD
         
         Bit 5 represents Inventory
         
         "
    ::= { gamLldpStatusMedRemoteDeviceInfoEntry 4 }

gamLldpStatusMedRemoteDeviceInfoCapabilitiesEnabled OBJECT-TYPE
    SYNTAX      GAMUnsigned16
    MAX-ACCESS  read-only
    STATUS      current
    DESCRIPTION
        "LLDP neighbor's capabilities bit mask for the capabilities which are
         currently enabled.
         
         Bit 0 represents LLDP-MED capabilities.
         
         Bit 1 represents Network Policy.
         
         Bit 2 represents Location Identification.
         
         Bit 3 represents Extended Power via MDI - PSE.
         
         Bit 4 represents Extended Power via MDI - PD
         
         Bit 5 represents Inventory
         
         "
    ::= { gamLldpStatusMedRemoteDeviceInfoEntry 5 }

gamLldpStatusMedRemoteDeviceInfoLatitude OBJECT-TYPE
    SYNTAX      GAMInteger64
    MAX-ACCESS  read-only
    STATUS      current
    DESCRIPTION
        "Latitude degrees in 2s-complement as specified in RFC 3825. Positive
         numbers are north of the equator and negative numbers are south of the
         equator."
    ::= { gamLldpStatusMedRemoteDeviceInfoEntry 6 }

gamLldpStatusMedRemoteDeviceInfoLongitude OBJECT-TYPE
    SYNTAX      GAMInteger64
    MAX-ACCESS  read-only
    STATUS      current
    DESCRIPTION
        "Longitude degrees in 2s-complement as specified in RFC 3825. Positive
         values are East of the prime meridian and negative numbers are West of
         the prime meridian."
    ::= { gamLldpStatusMedRemoteDeviceInfoEntry 7 }

gamLldpStatusMedRemoteDeviceInfoAltitudeType OBJECT-TYPE
    SYNTAX      GAMLldpMedAltitudeType
    MAX-ACCESS  read-only
    STATUS      current
    DESCRIPTION
        "Altitude type as either floors or meters. Meters are representing
         meters of altitude defined by the vertical datum specified. Floors are
         representing altitude in a form more relevant in buildings which have
         different floor-to-floor dimensions. An altitude = 0.0 is meaningful
         even outside a building, and represents ground level at the given
         latitude and longitude. Inside a building, 0.0 represents the floor
         level associated with ground level at the main entrance."
    ::= { gamLldpStatusMedRemoteDeviceInfoEntry 8 }

gamLldpStatusMedRemoteDeviceInfoAltitude OBJECT-TYPE
    SYNTAX      Integer32
    MAX-ACCESS  read-only
    STATUS      current
    DESCRIPTION
        "Altitude value in 2s-complement as specified in RFC 3825"
    ::= { gamLldpStatusMedRemoteDeviceInfoEntry 9 }

gamLldpStatusMedRemoteDeviceInfoDatum OBJECT-TYPE
    SYNTAX      GAMLldpMedDatumType
    MAX-ACCESS  read-only
    STATUS      current
    DESCRIPTION
        "Datum (geodetic system) .
         
         The Map Datum is used for the coordinates given in these options:
         
         WGS84: (Geographical 3D) - World Geodesic System 1984, CRS Code 4327,
         Prime Meridian Name: Greenwich.
         
         NAD83/NAVD88: North American Datum 1983, CRS Code 4269, Prime Meridian
         Name: Greenwich; The associated vertical datum is the North American
         Vertical Datum of 1988 (NAVD88). This datum pair is to be used when
         referencing locations on land, not near tidal water(which would use
         Datum = NAD83/MLLW).
         
         NAD83/MLLW: North American Datum 1983, CRS Code 4269, Prime Meridian
         Name: Greenwich; The associated vertical datum is Mean Lower Low Water
         (MLLW). This datum pair is to be used when referencing locations on
         water/sea/ocean."
    ::= { gamLldpStatusMedRemoteDeviceInfoEntry 10 }

gamLldpStatusMedRemoteDeviceInfoElinaddr OBJECT-TYPE
    SYNTAX      GAMDisplayString (SIZE(0..25))
    MAX-ACCESS  read-only
    STATUS      current
    DESCRIPTION
        "Emergency Call Service ELIN identifier data format is defined to carry
         the ELIN identifier as used during emergency call setup to a
         traditional CAMA or ISDN trunk-based PSAP. This format consists of a
         numerical digit string, corresponding to the ELIN to be used for
         emergency calling. Maximum number of octets are 25."
    ::= { gamLldpStatusMedRemoteDeviceInfoEntry 11 }

gamLldpStatusMedRemoteDeviceInfoDeviceType OBJECT-TYPE
    SYNTAX      GAMLldpMedRemoteDeviceType
    MAX-ACCESS  read-only
    STATUS      current
    DESCRIPTION
        "Shows the LLDP neighbor's device type."
    ::= { gamLldpStatusMedRemoteDeviceInfoEntry 12 }

gamLldpStatusMedRemoteDeviceInfoHwRev OBJECT-TYPE
    SYNTAX      GAMDisplayString (SIZE(0..31))
    MAX-ACCESS  read-only
    STATUS      current
    DESCRIPTION
        "Shows the LLDP neighbor's hardware revision."
    ::= { gamLldpStatusMedRemoteDeviceInfoEntry 13 }

gamLldpStatusMedRemoteDeviceInfoFwRev OBJECT-TYPE
    SYNTAX      GAMDisplayString (SIZE(0..31))
    MAX-ACCESS  read-only
    STATUS      current
    DESCRIPTION
        "Shows the LLDP neighbor's firmware revision."
    ::= { gamLldpStatusMedRemoteDeviceInfoEntry 14 }

gamLldpStatusMedRemoteDeviceInfoSwRev OBJECT-TYPE
    SYNTAX      GAMDisplayString (SIZE(0..31))
    MAX-ACCESS  read-only
    STATUS      current
    DESCRIPTION
        "Shows the LLDP neighbor's software revision."
    ::= { gamLldpStatusMedRemoteDeviceInfoEntry 15 }

gamLldpStatusMedRemoteDeviceInfoSerialNo OBJECT-TYPE
    SYNTAX      GAMDisplayString (SIZE(0..31))
    MAX-ACCESS  read-only
    STATUS      current
    DESCRIPTION
        "Shows the LLDP neighbor's serial number."
    ::= { gamLldpStatusMedRemoteDeviceInfoEntry 16 }

gamLldpStatusMedRemoteDeviceInfoManufacturerName OBJECT-TYPE
    SYNTAX      GAMDisplayString (SIZE(0..31))
    MAX-ACCESS  read-only
    STATUS      current
    DESCRIPTION
        "Shows the LLDP neighbor's manufacturer name."
    ::= { gamLldpStatusMedRemoteDeviceInfoEntry 17 }

gamLldpStatusMedRemoteDeviceInfoModelName OBJECT-TYPE
    SYNTAX      GAMDisplayString (SIZE(0..31))
    MAX-ACCESS  read-only
    STATUS      current
    DESCRIPTION
        "Shows the LLDP neighbor's model name."
    ::= { gamLldpStatusMedRemoteDeviceInfoEntry 18 }

gamLldpStatusMedRemoteDeviceInfoAssetId OBJECT-TYPE
    SYNTAX      GAMDisplayString (SIZE(0..31))
    MAX-ACCESS  read-only
    STATUS      current
    DESCRIPTION
        "Shows the LLDP neighbor's asset id."
    ::= { gamLldpStatusMedRemoteDeviceInfoEntry 19 }

gamLldpStatusMedRemoteDeviceInfoEeeRxTwSys OBJECT-TYPE
    SYNTAX      GAMUnsigned16
    MAX-ACCESS  read-only
    STATUS      current
    DESCRIPTION
        "Shows the LLDP neighbor's Receive tw_sys_rx . Tw_sys_rx is defined as
         the time (expressed in microseconds) that the transmitting link partner
         will wait before it starts transmitting data after leaving the Low
         Power Idle (LPI) mode. Section 79.3.5.2, IEEE802.3az."
    ::= { gamLldpStatusMedRemoteDeviceInfoEntry 20 }

gamLldpStatusMedRemoteDeviceInfoEeeTxTwSys OBJECT-TYPE
    SYNTAX      GAMUnsigned16
    MAX-ACCESS  read-only
    STATUS      current
    DESCRIPTION
        "Shows the LLDP neighbor's Transmit Tw_sys_tx . Tw_sys_tx is defined as
         the time (expressed in microseconds) that the receiving link partner is
         requesting the transmitting link partner to wait before starting the
         transmission data following the Low Power Idle (LPI) mode. Section
         79.3.5.1, IEEE802.3az."
    ::= { gamLldpStatusMedRemoteDeviceInfoEntry 21 }

gamLldpStatusMedRemoteDeviceInfoEeeFbTwSys OBJECT-TYPE
    SYNTAX      GAMUnsigned16
    MAX-ACCESS  read-only
    STATUS      current
    DESCRIPTION
        "Shows the LLDP neighbor's Fallback tw_sys_tx. A receiving link partner
         may inform the transmitter of an alternate desired Tw_sys_tx. Since a
         receiving link partner is likely to have discrete levels for savings,
         this provides the transmitter with additional information that it may
         use for a more efficient allocation. Section 79.3.5.3, IEEE802.3az."
    ::= { gamLldpStatusMedRemoteDeviceInfoEntry 22 }

gamLldpStatusMedRemoteDeviceInfoEeeTxTwSysEcho OBJECT-TYPE
    SYNTAX      GAMUnsigned16
    MAX-ACCESS  read-only
    STATUS      current
    DESCRIPTION
        "Shows the LLDP neighbor's echo transmit Tw. The respective echo values
         shall be defined as the local link partners reflection (echo) of the
         remote link partners respective values. When a local link partner
         receives its echoed values from the remote link partner it can
         determine whether or not the remote link partner has received,
         registered, and processed its most recent values. Section 79.3.5.4,
         IEEE802.3az."
    ::= { gamLldpStatusMedRemoteDeviceInfoEntry 23 }

gamLldpStatusMedRemoteDeviceInfoEeeRxTwSysEcho OBJECT-TYPE
    SYNTAX      GAMUnsigned16
    MAX-ACCESS  read-only
    STATUS      current
    DESCRIPTION
        "Shows the LLDP neighbor's echo receive Tw. The respective echo values
         shall be defined as the local link partners reflection (echo) of the
         remote link partners respective values. When a local link partner
         receives its echoed values from the remote link partner it can
         determine whether or not the remote link partner has received,
         registered, and processed its most recent values. Section 79.3.5.4,
         IEEE802.3az."
    ::= { gamLldpStatusMedRemoteDeviceInfoEntry 24 }

gamLldpStatusMedRemoteDeviceLocInfoTable OBJECT-TYPE
    SYNTAX      SEQUENCE OF GAMLldpStatusMedRemoteDeviceLocInfoEntry
    MAX-ACCESS  not-accessible
    STATUS      current
    DESCRIPTION
        "This is a table to show the LLDP-MED remote device (neighbor) civic
         location information for a specific interface."
    ::= { gamLldpStatusMed 2 }

gamLldpStatusMedRemoteDeviceLocInfoEntry OBJECT-TYPE
    SYNTAX      GAMLldpStatusMedRemoteDeviceLocInfoEntry
    MAX-ACCESS  not-accessible
    STATUS      current
    DESCRIPTION
        "Each interface has a set of neighbors information"
    INDEX       { gamLldpStatusMedRemoteDeviceLocInfoIfIndex,
                  gamLldpStatusMedRemoteDeviceLocInfoLldpmedIndex }
    ::= { gamLldpStatusMedRemoteDeviceLocInfoTable 1 }

GAMLldpStatusMedRemoteDeviceLocInfoEntry ::= SEQUENCE {
    gamLldpStatusMedRemoteDeviceLocInfoIfIndex                 GAMInterfaceIndex,
    gamLldpStatusMedRemoteDeviceLocInfoLldpmedIndex            Integer32,
    gamLldpStatusMedRemoteDeviceLocInfoState                   GAMDisplayString,
    gamLldpStatusMedRemoteDeviceLocInfoCounty                  GAMDisplayString,
    gamLldpStatusMedRemoteDeviceLocInfoCity                    GAMDisplayString,
    gamLldpStatusMedRemoteDeviceLocInfoDistrict                GAMDisplayString,
    gamLldpStatusMedRemoteDeviceLocInfoBlock                   GAMDisplayString,
    gamLldpStatusMedRemoteDeviceLocInfoStreet                  GAMDisplayString,
    gamLldpStatusMedRemoteDeviceLocInfoLeadingStreetDirection  GAMDisplayString,
    gamLldpStatusMedRemoteDeviceLocInfoTrailingStreetSuffix    GAMDisplayString,
    gamLldpStatusMedRemoteDeviceLocInfoStreetSuffix            GAMDisplayString,
    gamLldpStatusMedRemoteDeviceLocInfoHouseNo                 GAMDisplayString,
    gamLldpStatusMedRemoteDeviceLocInfoHouseNoSuffix           GAMDisplayString,
    gamLldpStatusMedRemoteDeviceLocInfoLandmark                GAMDisplayString,
    gamLldpStatusMedRemoteDeviceLocInfoAdditionalInfo          GAMDisplayString,
    gamLldpStatusMedRemoteDeviceLocInfoName                    GAMDisplayString,
    gamLldpStatusMedRemoteDeviceLocInfoZipCode                 GAMDisplayString,
    gamLldpStatusMedRemoteDeviceLocInfoBuilding                GAMDisplayString,
    gamLldpStatusMedRemoteDeviceLocInfoApartment               GAMDisplayString,
    gamLldpStatusMedRemoteDeviceLocInfoFloor                   GAMDisplayString,
    gamLldpStatusMedRemoteDeviceLocInfoRoomNumber              GAMDisplayString,
    gamLldpStatusMedRemoteDeviceLocInfoPlaceType               GAMDisplayString,
    gamLldpStatusMedRemoteDeviceLocInfoPostalCommunityName     GAMDisplayString,
    gamLldpStatusMedRemoteDeviceLocInfoPoBox                   GAMDisplayString,
    gamLldpStatusMedRemoteDeviceLocInfoAdditionalCode          GAMDisplayString,
    gamLldpStatusMedRemoteDeviceLocInfoCountryCode             GAMDisplayString
}

gamLldpStatusMedRemoteDeviceLocInfoIfIndex OBJECT-TYPE
    SYNTAX      GAMInterfaceIndex
    MAX-ACCESS  accessible-for-notify
    STATUS      current
    DESCRIPTION
        "Logical interface number index."
    ::= { gamLldpStatusMedRemoteDeviceLocInfoEntry 1 }

gamLldpStatusMedRemoteDeviceLocInfoLldpmedIndex OBJECT-TYPE
    SYNTAX      Integer32 (0..192)
    MAX-ACCESS  accessible-for-notify
    STATUS      current
    DESCRIPTION
        "Neighbor information table entry index."
    ::= { gamLldpStatusMedRemoteDeviceLocInfoEntry 2 }

gamLldpStatusMedRemoteDeviceLocInfoState OBJECT-TYPE
    SYNTAX      GAMDisplayString (SIZE(0..250))
    MAX-ACCESS  read-only
    STATUS      current
    DESCRIPTION
        "National subdivision"
    ::= { gamLldpStatusMedRemoteDeviceLocInfoEntry 5 }

gamLldpStatusMedRemoteDeviceLocInfoCounty OBJECT-TYPE
    SYNTAX      GAMDisplayString (SIZE(0..250))
    MAX-ACCESS  read-only
    STATUS      current
    DESCRIPTION
        "County"
    ::= { gamLldpStatusMedRemoteDeviceLocInfoEntry 6 }

gamLldpStatusMedRemoteDeviceLocInfoCity OBJECT-TYPE
    SYNTAX      GAMDisplayString (SIZE(0..250))
    MAX-ACCESS  read-only
    STATUS      current
    DESCRIPTION
        "City"
    ::= { gamLldpStatusMedRemoteDeviceLocInfoEntry 7 }

gamLldpStatusMedRemoteDeviceLocInfoDistrict OBJECT-TYPE
    SYNTAX      GAMDisplayString (SIZE(0..250))
    MAX-ACCESS  read-only
    STATUS      current
    DESCRIPTION
        "City district"
    ::= { gamLldpStatusMedRemoteDeviceLocInfoEntry 8 }

gamLldpStatusMedRemoteDeviceLocInfoBlock OBJECT-TYPE
    SYNTAX      GAMDisplayString (SIZE(0..250))
    MAX-ACCESS  read-only
    STATUS      current
    DESCRIPTION
        "Block (Neighborhood)"
    ::= { gamLldpStatusMedRemoteDeviceLocInfoEntry 9 }

gamLldpStatusMedRemoteDeviceLocInfoStreet OBJECT-TYPE
    SYNTAX      GAMDisplayString (SIZE(0..250))
    MAX-ACCESS  read-only
    STATUS      current
    DESCRIPTION
        "Street"
    ::= { gamLldpStatusMedRemoteDeviceLocInfoEntry 10 }

gamLldpStatusMedRemoteDeviceLocInfoLeadingStreetDirection OBJECT-TYPE
    SYNTAX      GAMDisplayString (SIZE(0..250))
    MAX-ACCESS  read-only
    STATUS      current
    DESCRIPTION
        "Street Direction"
    ::= { gamLldpStatusMedRemoteDeviceLocInfoEntry 11 }

gamLldpStatusMedRemoteDeviceLocInfoTrailingStreetSuffix OBJECT-TYPE
    SYNTAX      GAMDisplayString (SIZE(0..250))
    MAX-ACCESS  read-only
    STATUS      current
    DESCRIPTION
        "Trailing Street Suffix"
    ::= { gamLldpStatusMedRemoteDeviceLocInfoEntry 12 }

gamLldpStatusMedRemoteDeviceLocInfoStreetSuffix OBJECT-TYPE
    SYNTAX      GAMDisplayString (SIZE(0..250))
    MAX-ACCESS  read-only
    STATUS      current
    DESCRIPTION
        "Street Suffix"
    ::= { gamLldpStatusMedRemoteDeviceLocInfoEntry 13 }

gamLldpStatusMedRemoteDeviceLocInfoHouseNo OBJECT-TYPE
    SYNTAX      GAMDisplayString (SIZE(0..250))
    MAX-ACCESS  read-only
    STATUS      current
    DESCRIPTION
        "House No."
    ::= { gamLldpStatusMedRemoteDeviceLocInfoEntry 14 }

gamLldpStatusMedRemoteDeviceLocInfoHouseNoSuffix OBJECT-TYPE
    SYNTAX      GAMDisplayString (SIZE(0..250))
    MAX-ACCESS  read-only
    STATUS      current
    DESCRIPTION
        "House No. Suffix"
    ::= { gamLldpStatusMedRemoteDeviceLocInfoEntry 15 }

gamLldpStatusMedRemoteDeviceLocInfoLandmark OBJECT-TYPE
    SYNTAX      GAMDisplayString (SIZE(0..250))
    MAX-ACCESS  read-only
    STATUS      current
    DESCRIPTION
        "Landmark"
    ::= { gamLldpStatusMedRemoteDeviceLocInfoEntry 16 }

gamLldpStatusMedRemoteDeviceLocInfoAdditionalInfo OBJECT-TYPE
    SYNTAX      GAMDisplayString (SIZE(0..250))
    MAX-ACCESS  read-only
    STATUS      current
    DESCRIPTION
        "Additional Location Info"
    ::= { gamLldpStatusMedRemoteDeviceLocInfoEntry 17 }

gamLldpStatusMedRemoteDeviceLocInfoName OBJECT-TYPE
    SYNTAX      GAMDisplayString (SIZE(0..250))
    MAX-ACCESS  read-only
    STATUS      current
    DESCRIPTION
        "Name"
    ::= { gamLldpStatusMedRemoteDeviceLocInfoEntry 18 }

gamLldpStatusMedRemoteDeviceLocInfoZipCode OBJECT-TYPE
    SYNTAX      GAMDisplayString (SIZE(0..250))
    MAX-ACCESS  read-only
    STATUS      current
    DESCRIPTION
        "Zip code"
    ::= { gamLldpStatusMedRemoteDeviceLocInfoEntry 19 }

gamLldpStatusMedRemoteDeviceLocInfoBuilding OBJECT-TYPE
    SYNTAX      GAMDisplayString (SIZE(0..250))
    MAX-ACCESS  read-only
    STATUS      current
    DESCRIPTION
        "Building"
    ::= { gamLldpStatusMedRemoteDeviceLocInfoEntry 20 }

gamLldpStatusMedRemoteDeviceLocInfoApartment OBJECT-TYPE
    SYNTAX      GAMDisplayString (SIZE(0..250))
    MAX-ACCESS  read-only
    STATUS      current
    DESCRIPTION
        "Apartment/unit"
    ::= { gamLldpStatusMedRemoteDeviceLocInfoEntry 21 }

gamLldpStatusMedRemoteDeviceLocInfoFloor OBJECT-TYPE
    SYNTAX      GAMDisplayString (SIZE(0..250))
    MAX-ACCESS  read-only
    STATUS      current
    DESCRIPTION
        "Floor"
    ::= { gamLldpStatusMedRemoteDeviceLocInfoEntry 22 }

gamLldpStatusMedRemoteDeviceLocInfoRoomNumber OBJECT-TYPE
    SYNTAX      GAMDisplayString (SIZE(0..250))
    MAX-ACCESS  read-only
    STATUS      current
    DESCRIPTION
        "Room Number"
    ::= { gamLldpStatusMedRemoteDeviceLocInfoEntry 23 }

gamLldpStatusMedRemoteDeviceLocInfoPlaceType OBJECT-TYPE
    SYNTAX      GAMDisplayString (SIZE(0..250))
    MAX-ACCESS  read-only
    STATUS      current
    DESCRIPTION
        "Place type"
    ::= { gamLldpStatusMedRemoteDeviceLocInfoEntry 24 }

gamLldpStatusMedRemoteDeviceLocInfoPostalCommunityName OBJECT-TYPE
    SYNTAX      GAMDisplayString (SIZE(0..250))
    MAX-ACCESS  read-only
    STATUS      current
    DESCRIPTION
        "Postal Community Name"
    ::= { gamLldpStatusMedRemoteDeviceLocInfoEntry 25 }

gamLldpStatusMedRemoteDeviceLocInfoPoBox OBJECT-TYPE
    SYNTAX      GAMDisplayString (SIZE(0..250))
    MAX-ACCESS  read-only
    STATUS      current
    DESCRIPTION
        "Post Office Box"
    ::= { gamLldpStatusMedRemoteDeviceLocInfoEntry 26 }

gamLldpStatusMedRemoteDeviceLocInfoAdditionalCode OBJECT-TYPE
    SYNTAX      GAMDisplayString (SIZE(0..250))
    MAX-ACCESS  read-only
    STATUS      current
    DESCRIPTION
        "Additional Code"
    ::= { gamLldpStatusMedRemoteDeviceLocInfoEntry 27 }

gamLldpStatusMedRemoteDeviceLocInfoCountryCode OBJECT-TYPE
    SYNTAX      GAMDisplayString (SIZE(0..2))
    MAX-ACCESS  read-only
    STATUS      current
    DESCRIPTION
        "The two-letter ISO 3166 country code in capital ASCII letters -
         Example: DK, DE or US."
    ::= { gamLldpStatusMedRemoteDeviceLocInfoEntry 28 }

gamLldpStatusMedRemoteDeviceNetworkPolicyInfoTable OBJECT-TYPE
    SYNTAX      SEQUENCE OF GAMLldpStatusMedRemoteDeviceNetworkPolicyInfoEntry
    MAX-ACCESS  not-accessible
    STATUS      current
    DESCRIPTION
        "This is a table to show the LLDP-MED remote device (neighbor) network
         policies information for a specific interface."
    ::= { gamLldpStatusMed 3 }

gamLldpStatusMedRemoteDeviceNetworkPolicyInfoEntry OBJECT-TYPE
    SYNTAX      GAMLldpStatusMedRemoteDeviceNetworkPolicyInfoEntry
    MAX-ACCESS  not-accessible
    STATUS      current
    DESCRIPTION
        "Each interface has a set of neighbors information"
    INDEX       {                   gamLldpStatusMedRemoteDeviceNetworkPolicyInfoIfIndex,
                  gamLldpStatusMedRemoteDeviceNetworkPolicyInfoLldpmedIndex,
                  gamLldpStatusMedRemoteDeviceNetworkPolicyInfoLldpmedPolicy }
    ::= { gamLldpStatusMedRemoteDeviceNetworkPolicyInfoTable 1 }

GAMLldpStatusMedRemoteDeviceNetworkPolicyInfoEntry ::= SEQUENCE {
    gamLldpStatusMedRemoteDeviceNetworkPolicyInfoIfIndex          GAMInterfaceIndex,
    gamLldpStatusMedRemoteDeviceNetworkPolicyInfoLldpmedIndex     Integer32,
    gamLldpStatusMedRemoteDeviceNetworkPolicyInfoLldpmedPolicy    Integer32,
    gamLldpStatusMedRemoteDeviceNetworkPolicyInfoApplicationType  GAMLldpMedRemoteNetworkPolicyApplicationType,
    gamLldpStatusMedRemoteDeviceNetworkPolicyInfoUnknownPolicy    TruthValue,
    gamLldpStatusMedRemoteDeviceNetworkPolicyInfoTagged           TruthValue,
    gamLldpStatusMedRemoteDeviceNetworkPolicyInfoVlanId           GAMUnsigned16,
    gamLldpStatusMedRemoteDeviceNetworkPolicyInfoL2Priority       GAMUnsigned8,
    gamLldpStatusMedRemoteDeviceNetworkPolicyInfoDscp             GAMUnsigned8
}

gamLldpStatusMedRemoteDeviceNetworkPolicyInfoIfIndex OBJECT-TYPE
    SYNTAX      GAMInterfaceIndex
    MAX-ACCESS  accessible-for-notify
    STATUS      current
    DESCRIPTION
        "Logical interface number index."
    ::= { gamLldpStatusMedRemoteDeviceNetworkPolicyInfoEntry 1 }

gamLldpStatusMedRemoteDeviceNetworkPolicyInfoLldpmedIndex OBJECT-TYPE
    SYNTAX      Integer32 (0..192)
    MAX-ACCESS  accessible-for-notify
    STATUS      current
    DESCRIPTION
        "Neighbor information table entry index."
    ::= { gamLldpStatusMedRemoteDeviceNetworkPolicyInfoEntry 2 }

gamLldpStatusMedRemoteDeviceNetworkPolicyInfoLldpmedPolicy OBJECT-TYPE
    SYNTAX      Integer32 (0..31)
    MAX-ACCESS  accessible-for-notify
    STATUS      current
    DESCRIPTION
        "Policy index."
    ::= { gamLldpStatusMedRemoteDeviceNetworkPolicyInfoEntry 3 }

gamLldpStatusMedRemoteDeviceNetworkPolicyInfoApplicationType OBJECT-TYPE
    SYNTAX      GAMLldpMedRemoteNetworkPolicyApplicationType
    MAX-ACCESS  read-only
    STATUS      current
    DESCRIPTION
        "The LLDP policy application type."
    ::= { gamLldpStatusMedRemoteDeviceNetworkPolicyInfoEntry 5 }

gamLldpStatusMedRemoteDeviceNetworkPolicyInfoUnknownPolicy OBJECT-TYPE
    SYNTAX      TruthValue
    MAX-ACCESS  read-only
    STATUS      current
    DESCRIPTION
        "Policy indicates that an Endpoint Device wants to explicitly advertise
         that the policy is required by the device. Can be either Defined or
         Unknown
         
         Unknown: The network policy for the specified application type is
         currently unknown.
         
         Defined: The network policy is defined (known)."
    ::= { gamLldpStatusMedRemoteDeviceNetworkPolicyInfoEntry 6 }

gamLldpStatusMedRemoteDeviceNetworkPolicyInfoTagged OBJECT-TYPE
    SYNTAX      TruthValue
    MAX-ACCESS  read-only
    STATUS      current
    DESCRIPTION
        "Defines if LLDP policy uses tagged VLAN."
    ::= { gamLldpStatusMedRemoteDeviceNetworkPolicyInfoEntry 7 }

gamLldpStatusMedRemoteDeviceNetworkPolicyInfoVlanId OBJECT-TYPE
    SYNTAX      GAMUnsigned16 (1..4095)
    MAX-ACCESS  read-only
    STATUS      current
    DESCRIPTION
        "The policy VLAN ID. Only valid when policy 'Tagged' is TRUE"
    ::= { gamLldpStatusMedRemoteDeviceNetworkPolicyInfoEntry 8 }

gamLldpStatusMedRemoteDeviceNetworkPolicyInfoL2Priority OBJECT-TYPE
    SYNTAX      GAMUnsigned8 (0..7)
    MAX-ACCESS  read-only
    STATUS      current
    DESCRIPTION
        "Shows the LLDP neighbor's policy L2 priority."
    ::= { gamLldpStatusMedRemoteDeviceNetworkPolicyInfoEntry 9 }

gamLldpStatusMedRemoteDeviceNetworkPolicyInfoDscp OBJECT-TYPE
    SYNTAX      GAMUnsigned8 (0..63)
    MAX-ACCESS  read-only
    STATUS      current
    DESCRIPTION
        "LLDP policy DSCP."
    ::= { gamLldpStatusMedRemoteDeviceNetworkPolicyInfoEntry 10 }

gamLldpControl OBJECT IDENTIFIER
    ::= { gamLldpMibObjects 4 }

gamLldpControlStatisticsClear OBJECT IDENTIFIER
    ::= { gamLldpControl 1 }

gamLldpControlStatisticsClearTable OBJECT-TYPE
    SYNTAX      SEQUENCE OF GAMLldpControlStatisticsClearEntry
    MAX-ACCESS  not-accessible
    STATUS      current
    DESCRIPTION
        "This is a table to clear LLDP statistics for a specific interface."
    ::= { gamLldpControlStatisticsClear 1 }

gamLldpControlStatisticsClearEntry OBJECT-TYPE
    SYNTAX      GAMLldpControlStatisticsClearEntry
    MAX-ACCESS  not-accessible
    STATUS      current
    DESCRIPTION
        "Each interface has a set of statistics counters"
    INDEX       { gamLldpControlStatisticsClearIfIndex }
    ::= { gamLldpControlStatisticsClearTable 1 }

GAMLldpControlStatisticsClearEntry ::= SEQUENCE {
    gamLldpControlStatisticsClearIfIndex          GAMInterfaceIndex,
    gamLldpControlStatisticsClearStatisticsClear  TruthValue
}

gamLldpControlStatisticsClearIfIndex OBJECT-TYPE
    SYNTAX      GAMInterfaceIndex
    MAX-ACCESS  accessible-for-notify
    STATUS      current
    DESCRIPTION
        "Logical interface number index."
    ::= { gamLldpControlStatisticsClearEntry 1 }

gamLldpControlStatisticsClearStatisticsClear OBJECT-TYPE
    SYNTAX      TruthValue
    MAX-ACCESS  read-write
    STATUS      current
    DESCRIPTION
        "Set to TRUE to clear the LLDP statistics of an interface."
    ::= { gamLldpControlStatisticsClearEntry 2 }

gamLldpControlStatisticsClearGlobal OBJECT IDENTIFIER
    ::= { gamLldpControlStatisticsClear 2 }

gamLldpControlStatisticsClearGlobalClear OBJECT-TYPE
    SYNTAX      TruthValue
    MAX-ACCESS  read-write
    STATUS      current
    DESCRIPTION
        "Set to TRUE to clear the LLDP global statistics."
    ::= { gamLldpControlStatisticsClearGlobal 1 }

gamLldpMibConformance OBJECT IDENTIFIER
    ::= { gamLldpMib 2 }

gamLldpMibCompliances OBJECT IDENTIFIER
    ::= { gamLldpMibConformance 1 }

gamLldpMibGroups OBJECT IDENTIFIER
    ::= { gamLldpMibConformance 2 }

gamLldpConfigGlobalInfoGroup OBJECT-GROUP
    OBJECTS     { gamLldpConfigGlobalReInitDelay,
                  gamLldpConfigGlobalMsgTxHold,
                  gamLldpConfigGlobalMsgTxInterval,
                  gamLldpConfigGlobalTxDelay }
    STATUS      current
    DESCRIPTION
        "A collection of objects."
    ::= { gamLldpMibGroups 1 }

gamLldpConfigInfoGroup OBJECT-GROUP
    OBJECTS     { gamLldpConfigIfIndex, gamLldpConfigAdminState,
                  gamLldpConfigCdpAware, gamLldpConfigOptionalTlvs,
                  gamLldpConfigSnmpNotificationEna }
    STATUS      current
    DESCRIPTION
        "A collection of objects."
    ::= { gamLldpMibGroups 2 }

gamLldpConfigMedInfoGroup OBJECT-GROUP
    OBJECTS     { gamLldpConfigMedIfIndex,
                  gamLldpConfigMedOptionalTlvs,
                  gamLldpConfigMedDeviceType }
    STATUS      current
    DESCRIPTION
        "A collection of objects."
    ::= { gamLldpMibGroups 3 }

gamLldpConfigMedPolicyInfoGroup OBJECT-GROUP
    OBJECTS     { gamLldpConfigMedPolicyLldpmedPolicy,
                  gamLldpConfigMedPolicyApplicationType,
                  gamLldpConfigMedPolicyTagged,
                  gamLldpConfigMedPolicyVlanId,
                  gamLldpConfigMedPolicyL2Priority,
                  gamLldpConfigMedPolicyDscp,
                  gamLldpConfigMedPolicyAction }
    STATUS      current
    DESCRIPTION
        "A collection of objects."
    ::= { gamLldpMibGroups 4 }

gamLldpConfigMedPolicyListInfoGroup OBJECT-GROUP
    OBJECTS     { gamLldpConfigMedPolicyListIfIndex,
                  gamLldpConfigMedPolicyListLldpmedPolicy,
                  gamLldpConfigMedPolicyListLldpmedPoliciesList }
    STATUS      current
    DESCRIPTION
        "A collection of objects."
    ::= { gamLldpMibGroups 5 }

gamLldpConfigMedGlobalInfoGroup OBJECT-GROUP
    OBJECTS     { gamLldpConfigMedGlobalFastRepeatCount,
                  gamLldpConfigMedGlobalLatitude,
                  gamLldpConfigMedGlobalLongitude,
                  gamLldpConfigMedGlobalAltitudeType,
                  gamLldpConfigMedGlobalAltitude,
                  gamLldpConfigMedGlobalElinAddr,
                  gamLldpConfigMedGlobalDatum,
                  gamLldpConfigMedGlobalCountryCode }
    STATUS      current
    DESCRIPTION
        "A collection of objects."
    ::= { gamLldpMibGroups 6 }

gamLldpConfigMedLocationInformationInfoGroup OBJECT-GROUP
    OBJECTS     { gamLldpConfigMedLocationInformationLldpmedIndex,
                  gamLldpConfigMedLocationInformationCivicAddress }
    STATUS      current
    DESCRIPTION
        "A collection of objects."
    ::= { gamLldpMibGroups 7 }

gamLldpConfigMedPolicyRowEditorInfoGroup OBJECT-GROUP
    OBJECTS     { gamLldpConfigMedPolicyRowEditorLldpmedPolicy,
                  gamLldpConfigMedPolicyRowEditorApplicationType,
                  gamLldpConfigMedPolicyRowEditorTagged,
                  gamLldpConfigMedPolicyRowEditorVlanId,
                  gamLldpConfigMedPolicyRowEditorL2Priority,
                  gamLldpConfigMedPolicyRowEditorDscp,
                  gamLldpConfigMedPolicyRowEditorAction }
    STATUS      current
    DESCRIPTION
        "A collection of objects."
    ::= { gamLldpMibGroups 8 }

gamLldpStatusStatisticsGlobalCountersInfoGroup OBJECT-GROUP
    OBJECTS     { gamLldpStatusStatisticsGlobalCountersTableInserts,
                  gamLldpStatusStatisticsGlobalCountersTableDeletes,
                  gamLldpStatusStatisticsGlobalCountersTableDrops,
                  gamLldpStatusStatisticsGlobalCountersTableAgeOuts,
                  gamLldpStatusStatisticsGlobalCountersLastChangeTime }
    STATUS      current
    DESCRIPTION
        "A collection of objects."
    ::= { gamLldpMibGroups 9 }

gamLldpStatusStatisticsTableInfoGroup OBJECT-GROUP
    OBJECTS     { gamLldpStatusStatisticsIfIndex,
                  gamLldpStatusStatisticsTxTotal,
                  gamLldpStatusStatisticsRxTotal,
                  gamLldpStatusStatisticsRxError,
                  gamLldpStatusStatisticsRxDiscarded,
                  gamLldpStatusStatisticsTLVsDiscarded,
                  gamLldpStatusStatisticsTLVsUnrecognized,
                  gamLldpStatusStatisticsTLVsOrgDiscarded,
                  gamLldpStatusStatisticsAgeOuts }
    STATUS      current
    DESCRIPTION
        "A collection of objects."
    ::= { gamLldpMibGroups 10 }

gamLldpStatusNeighborsInformationInfoGroup OBJECT-GROUP
    OBJECTS     { gamLldpStatusNeighborsInformationIfIndex,
                  gamLldpStatusNeighborsInformationLldpmedIndex,
                  gamLldpStatusNeighborsInformationChassisId,
                  gamLldpStatusNeighborsInformationPortId,
                  gamLldpStatusNeighborsInformationPortDescription,
                  gamLldpStatusNeighborsInformationSystemName,
                  gamLldpStatusNeighborsInformationSystemDescription,
                  gamLldpStatusNeighborsInformationSystemCapabilities,
                  gamLldpStatusNeighborsInformationSystemCapabilitiesEnable }
    STATUS      current
    DESCRIPTION
        "A collection of objects."
    ::= { gamLldpMibGroups 11 }

gamLldpStatusNeighborsMgmtInformationInfoGroup OBJECT-GROUP
    OBJECTS     { gamLldpStatusNeighborsMgmtInformationIfIndex,
                  gamLldpStatusNeighborsMgmtInformationLldpmedIndex,
                  gamLldpStatusNeighborsMgmtInformationLldpManagement,
                  gamLldpStatusNeighborsMgmtInformationSystemMgmAddressSubtype,
                  gamLldpStatusNeighborsMgmtInformationSystemMgmtAddress,
                  gamLldpStatusNeighborsMgmtInformationSystemMgmtInterfaceSubtype,
                  gamLldpStatusNeighborsMgmtInformationSystemMgmtInterface,
                  gamLldpStatusNeighborsMgmtInformationSystemMgmtOid }
    STATUS      current
    DESCRIPTION
        "A collection of objects."
    ::= { gamLldpMibGroups 12 }

gamLldpStatusPreemptInformationInfoGroup OBJECT-GROUP
    OBJECTS     { gamLldpStatusPreemptInformationIfIndex,
                  gamLldpStatusPreemptInformationLldpmedIndex,
                  gamLldpStatusPreemptInformationLldpManagement,
                  gamLldpStatusPreemptInformationLocPreemptSupported,
                  gamLldpStatusPreemptInformationLocPreemptEnabled,
                  gamLldpStatusPreemptInformationLocPreemptActive,
                  gamLldpStatusPreemptInformationLocAddFragSize,
                  gamLldpStatusPreemptInformationRemFramePreemptSupported,
                  gamLldpStatusPreemptInformationRemFramePreemptEnabled,
                  gamLldpStatusPreemptInformationRemFramePreemptActive,
                  gamLldpStatusPreemptInformationRemFrameAddFragSize }
    STATUS      current
    DESCRIPTION
        "A collection of objects."
    ::= { gamLldpMibGroups 13 }

gamLldpStatusMedRemoteDeviceInfoInfoGroup OBJECT-GROUP
    OBJECTS     { gamLldpStatusMedRemoteDeviceInfoIfIndex,
                  gamLldpStatusMedRemoteDeviceInfoLldpmedIndex,
                  gamLldpStatusMedRemoteDeviceInfoCapabilities,
                  gamLldpStatusMedRemoteDeviceInfoCapabilitiesEnabled,
                  gamLldpStatusMedRemoteDeviceInfoLatitude,
                  gamLldpStatusMedRemoteDeviceInfoLongitude,
                  gamLldpStatusMedRemoteDeviceInfoAltitudeType,
                  gamLldpStatusMedRemoteDeviceInfoAltitude,
                  gamLldpStatusMedRemoteDeviceInfoDatum,
                  gamLldpStatusMedRemoteDeviceInfoElinaddr,
                  gamLldpStatusMedRemoteDeviceInfoDeviceType,
                  gamLldpStatusMedRemoteDeviceInfoHwRev,
                  gamLldpStatusMedRemoteDeviceInfoFwRev,
                  gamLldpStatusMedRemoteDeviceInfoSwRev,
                  gamLldpStatusMedRemoteDeviceInfoSerialNo,
                  gamLldpStatusMedRemoteDeviceInfoManufacturerName,
                  gamLldpStatusMedRemoteDeviceInfoModelName,
                  gamLldpStatusMedRemoteDeviceInfoAssetId,
                  gamLldpStatusMedRemoteDeviceInfoEeeRxTwSys,
                  gamLldpStatusMedRemoteDeviceInfoEeeTxTwSys,
                  gamLldpStatusMedRemoteDeviceInfoEeeFbTwSys,
                  gamLldpStatusMedRemoteDeviceInfoEeeTxTwSysEcho,
                  gamLldpStatusMedRemoteDeviceInfoEeeRxTwSysEcho }
    STATUS      current
    DESCRIPTION
        "A collection of objects."
    ::= { gamLldpMibGroups 14 }

gamLldpStatusMedRemoteDeviceLocInfoInfoGroup OBJECT-GROUP
    OBJECTS     { gamLldpStatusMedRemoteDeviceLocInfoIfIndex,
                  gamLldpStatusMedRemoteDeviceLocInfoLldpmedIndex,
                  gamLldpStatusMedRemoteDeviceLocInfoState,
                  gamLldpStatusMedRemoteDeviceLocInfoCounty,
                  gamLldpStatusMedRemoteDeviceLocInfoCity,
                  gamLldpStatusMedRemoteDeviceLocInfoDistrict,
                  gamLldpStatusMedRemoteDeviceLocInfoBlock,
                  gamLldpStatusMedRemoteDeviceLocInfoStreet,
                  gamLldpStatusMedRemoteDeviceLocInfoLeadingStreetDirection,
                  gamLldpStatusMedRemoteDeviceLocInfoTrailingStreetSuffix,
                  gamLldpStatusMedRemoteDeviceLocInfoStreetSuffix,
                  gamLldpStatusMedRemoteDeviceLocInfoHouseNo,
                  gamLldpStatusMedRemoteDeviceLocInfoHouseNoSuffix,
                  gamLldpStatusMedRemoteDeviceLocInfoLandmark,
                  gamLldpStatusMedRemoteDeviceLocInfoAdditionalInfo,
                  gamLldpStatusMedRemoteDeviceLocInfoName,
                  gamLldpStatusMedRemoteDeviceLocInfoZipCode,
                  gamLldpStatusMedRemoteDeviceLocInfoBuilding,
                  gamLldpStatusMedRemoteDeviceLocInfoApartment,
                  gamLldpStatusMedRemoteDeviceLocInfoFloor,
                  gamLldpStatusMedRemoteDeviceLocInfoRoomNumber,
                  gamLldpStatusMedRemoteDeviceLocInfoPlaceType,
                  gamLldpStatusMedRemoteDeviceLocInfoPostalCommunityName,
                  gamLldpStatusMedRemoteDeviceLocInfoPoBox,
                  gamLldpStatusMedRemoteDeviceLocInfoAdditionalCode,
                  gamLldpStatusMedRemoteDeviceLocInfoCountryCode }
    STATUS      current
    DESCRIPTION
        "A collection of objects."
    ::= { gamLldpMibGroups 15 }

gamLldpStatusMedRemoteDeviceNetworkPolicyInfoInfoGroup OBJECT-GROUP
    OBJECTS     {                   gamLldpStatusMedRemoteDeviceNetworkPolicyInfoIfIndex,
                  gamLldpStatusMedRemoteDeviceNetworkPolicyInfoLldpmedIndex,
                  gamLldpStatusMedRemoteDeviceNetworkPolicyInfoLldpmedPolicy,
                  gamLldpStatusMedRemoteDeviceNetworkPolicyInfoApplicationType,
                  gamLldpStatusMedRemoteDeviceNetworkPolicyInfoUnknownPolicy,
                  gamLldpStatusMedRemoteDeviceNetworkPolicyInfoTagged,
                  gamLldpStatusMedRemoteDeviceNetworkPolicyInfoVlanId,
                  gamLldpStatusMedRemoteDeviceNetworkPolicyInfoL2Priority,
                  gamLldpStatusMedRemoteDeviceNetworkPolicyInfoDscp }
    STATUS      current
    DESCRIPTION
        "A collection of objects."
    ::= { gamLldpMibGroups 16 }

gamLldpControlStatisticsClearTableInfoGroup OBJECT-GROUP
    OBJECTS     { gamLldpControlStatisticsClearIfIndex,
                  gamLldpControlStatisticsClearStatisticsClear }
    STATUS      current
    DESCRIPTION
        "A collection of objects."
    ::= { gamLldpMibGroups 17 }

gamLldpControlStatisticsClearGlobalInfoGroup OBJECT-GROUP
    OBJECTS     { gamLldpControlStatisticsClearGlobalClear }
    STATUS      current
    DESCRIPTION
        "A collection of objects."
    ::= { gamLldpMibGroups 18 }

gamLldpMibCompliance MODULE-COMPLIANCE
    STATUS      current
    DESCRIPTION
        "The compliance statement for the implementation."

    MODULE      -- this module

    MANDATORY-GROUPS { gamLldpConfigGlobalInfoGroup,
                       gamLldpConfigInfoGroup,
                       gamLldpConfigMedInfoGroup,
                       gamLldpConfigMedPolicyInfoGroup,
                       gamLldpConfigMedPolicyListInfoGroup,
                       gamLldpConfigMedGlobalInfoGroup,
                       gamLldpConfigMedLocationInformationInfoGroup,
                       gamLldpConfigMedPolicyRowEditorInfoGroup,
                       gamLldpStatusStatisticsGlobalCountersInfoGroup,
                       gamLldpStatusStatisticsTableInfoGroup,
                       gamLldpStatusNeighborsInformationInfoGroup,
                       gamLldpStatusNeighborsMgmtInformationInfoGroup,
                       gamLldpStatusPreemptInformationInfoGroup,
                       gamLldpStatusMedRemoteDeviceInfoInfoGroup,
                       gamLldpStatusMedRemoteDeviceLocInfoInfoGroup,
                       gamLldpStatusMedRemoteDeviceNetworkPolicyInfoInfoGroup,
                       gamLldpControlStatisticsClearTableInfoGroup,
                       gamLldpControlStatisticsClearGlobalInfoGroup }

    ::= { gamLldpMibCompliances 1 }

END
