-- *****************************************************************
-- QOS-MIB:  Positron's GAM private MIB
-- *****************************************************************

GAM-QOS-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    Dscp FROM DIFFSERV-DSCP-TC
    GAMASRType FROM GAM-TC
    GAMBitType FROM GAM-TC
    GAMDestMacType FROM GAM-TC
    GAMEtherType FROM GAM-TC
    GAMInteger16 FROM GAM-TC
    GAMInteger8 FROM GAM-TC
    GAMInterfaceIndex FROM GAM-TC
    GAMPercent FROM GAM-TC
    GAMPortList FROM GAM-TC
    GAMQosShaperRateType FROM GAM-TC
    GAMRowEditorState FROM GAM-TC
    GAMUnsigned16 FROM GAM-TC
    GAMUnsigned64 FROM GAM-TC
    GAMUnsigned8 FROM GAM-TC
    GAMVcapKeyType FROM GAM-TC
    GAMVlanTagPriority FROM GAM-TC
    GAMVlanTagType FROM GAM-TC
    IEEE8021STPTPtimeValue FROM IEEE8021-ST-MIB
    InetAddressIPv6 FROM INET-ADDRESS-MIB
    Counter64 FROM SNMPv2-SMI
    Integer32 FROM SNMPv2-SMI
    IpAddress FROM SNMPv2-SMI
    Unsigned32 FROM SNMPv2-SMI
    MacAddress FROM SNMPv2-TC
    TruthValue FROM SNMPv2-TC
    ;

gamQosMib MODULE-IDENTITY
    LAST-UPDATED "201711270000Z"
    ORGANIZATION
        "Positron Access Solutions Corp."
    CONTACT-INFO
        "Customer Service <info@positronaccess.com>"
    DESCRIPTION
        "This is a private MIB for QoS"
    REVISION    "201711270000Z"
    DESCRIPTION
        "Added MPLS TC capability test. Split AdminBaseTimes into Secs and
         NanoSecs. Updated various descriptions slightly."
    REVISION    "201703200000Z"
    DESCRIPTION
        "Added Frame Preemption support. Added PSFP support."
    REVISION    "201610170000Z"
    DESCRIPTION
        "Updated table dependencies and descriptions. Added new capability
         element for Wred"
    REVISION    "201602250000Z"
    DESCRIPTION
        "Added QosCapabilitiesHasQueueCutThrough object."
    REVISION    "201602110000Z"
    DESCRIPTION
        "Added QosCapabilitiesHasQueueShapersCredit object."
    REVISION    "201601190000Z"
    DESCRIPTION
        "Added (IEEE 802.1Qbv) Time Aware Shaper support."
    REVISION    "201511130000Z"
    DESCRIPTION
        "Updated descriptions."
    REVISION    "201509300000Z"
    DESCRIPTION
        "Added QosConfigInterfaceCosId."
    REVISION    "201508130000Z"
    DESCRIPTION
        "Changed to use Dscp types in QCEs."
    REVISION    "201506230000Z"
    DESCRIPTION
        "Removed QosConfigIngressMapPcpAction, QosConfigIngressMapDscpAction,
         QosConfigEgressMapCosidAction and QosConfigEgressMapDscpAction objects."
    REVISION    "201505270000Z"
    DESCRIPTION
        "Added QosConfigIngressMap, QosConfigEgressMap objects and related
         changes."
    REVISION    "201504070000Z"
    DESCRIPTION
        "Added QosConfigInterfaceQueueShaperRateType,
         QosConfigInterfaceShaperRateType objects."
    REVISION    "201411060000Z"
    DESCRIPTION
        "Added new WredV3 related objects and adapted WredTable to WredV3."
    REVISION    "201410080000Z"
    DESCRIPTION
        "Removed QosCapabilitiesBitrateMin, QosCapabilitiesBitrateMax,
         QosCapabilitiesBurstSizeMin and QosCapabilitiesBurstSizeMax.
         
         Added policer and shaper specific min/max capabilities objects.
         
         Added QosConfigGlobalStormPolicersUnicastFrameRate,
         QosConfigGlobalStormPolicersMulticastFrameRate and
         QosConfigGlobalStormPolicersBroadcastFrameRate."
    REVISION    "201409170000Z"
    DESCRIPTION
        "Added QosCapabilitiesHasQueueShapersExcess object."
    REVISION    "201408120000Z"
    DESCRIPTION
        "Updated descriptions when referring to a capability."
    REVISION    "201407010000Z"
    DESCRIPTION
        "Initial version"
    ::= { gamMgmt 14 }


GAMQosDscpClassify ::= TEXTUAL-CONVENTION
    STATUS      current
    DESCRIPTION
        "An integer that indicates the DSCP classify mode."
    SYNTAX      INTEGER { none(0), zero(1), selected(2), all(3) }

GAMQosDscpRemark ::= TEXTUAL-CONVENTION
    STATUS      current
    DESCRIPTION
        "An integer that indicates the DSCP remark mode."
    SYNTAX      INTEGER { disabled(0), rewrite(1), remap(2),
                          remapDp(3) }

GAMQosEgressMapKey ::= TEXTUAL-CONVENTION
    STATUS      current
    DESCRIPTION
        "An integer that indicates the key to use when matching frames in the
         egress map.
         
         If the value is zero, use classified COS ID.
         
         If the value is one, use classified COS ID and DPL.
         
         If the value is two, use classified DSCP.
         
         If the value is three, use classified DSCP and DPL.
         
         If the value is four, use classified MPLS TC.
         
         "
    SYNTAX      INTEGER { cosid(0), cosidDpl(1), dscp(2), dscpDpl(3),
                          tc(4), tcDpl(5) }

GAMQosIngressMapKey ::= TEXTUAL-CONVENTION
    STATUS      current
    DESCRIPTION
        "An integer that indicates the key to use when matching frames in the
         ingress map.
         
         If the value is zero, use PCP for tagged frames and none for the rest.
         
         If the value is one, use PCP/DEI for tagged frames and none for the
         rest.
         
         If the value is two, use DSCP as key for IP frames and none for the
         rest.
         
         If the value is three, use DSCP as key for IP frames, PCP/DEI for
         tagged frames and none for the rest.
         
         If the value is four, use MPLS TC as key for frames.
         
         "
    SYNTAX      INTEGER { pcp(0), pcpDei(1), dscp(2), dscpPcpDei(3),
                          tc(4) }

GAMQosMmStatusVerify ::= TEXTUAL-CONVENTION
    STATUS      current
    DESCRIPTION
        "An integer that indicates the status of the MAC Merge sublayer
         verification on the given device."
    SYNTAX      INTEGER { unknown(0), initial(1), verifying(2),
                          succeeded(3), failed(4), disabled(5) }

GAMQosQceFrameType ::= TEXTUAL-CONVENTION
    STATUS      current
    DESCRIPTION
        "An integer that indicates the QCE frame type key."
    SYNTAX      INTEGER { any(0), etype(1), llc(2), snap(3), ipv4(4),
                          ipv6(5) }

GAMQosQceUserType ::= TEXTUAL-CONVENTION
    STATUS      current
    DESCRIPTION
        "An integer that indicates the QCE user type.
         
         If the value is zero it indicates a static configuration.
         
         If the value is non-zero it indicates a dynamic configuration made by
         another subsystem."
    SYNTAX      INTEGER { admin(0), voiceVlan(1), ghn(2) }

GAMQosTagRemarkingMode ::= TEXTUAL-CONVENTION
    STATUS      current
    DESCRIPTION
        "An integer that indicates the tag remarking mode."
    SYNTAX      INTEGER { classified(0), default(2), mapped(3) }

GAMQosWredMaxSelector ::= TEXTUAL-CONVENTION
    STATUS      current
    DESCRIPTION
        "An integer that selects between 'Maximum Drop Probability' or 'Maximum
         Fill Level'."
    SYNTAX      INTEGER { maximumDropProbability(0),
                          maximumFillLevel(1) }

gamQosMibObjects OBJECT IDENTIFIER
    ::= { gamQosMib 1 }

gamQosCapabilities OBJECT IDENTIFIER
    ::= { gamQosMibObjects 1 }

gamQosCapabilitiesClassMin OBJECT-TYPE
    SYNTAX      Unsigned32
    MAX-ACCESS  read-only
    STATUS      current
    DESCRIPTION
        "Minimum allowed QoS class."
    ::= { gamQosCapabilities 1 }

gamQosCapabilitiesClassMax OBJECT-TYPE
    SYNTAX      Unsigned32
    MAX-ACCESS  read-only
    STATUS      current
    DESCRIPTION
        "Maximum allowed QoS class."
    ::= { gamQosCapabilities 2 }

gamQosCapabilitiesDplMin OBJECT-TYPE
    SYNTAX      GAMUnsigned8
    MAX-ACCESS  read-only
    STATUS      current
    DESCRIPTION
        "Minimum allowed drop precedence level."
    ::= { gamQosCapabilities 3 }

gamQosCapabilitiesDplMax OBJECT-TYPE
    SYNTAX      GAMUnsigned8
    MAX-ACCESS  read-only
    STATUS      current
    DESCRIPTION
        "Maximum allowed drop precedence level."
    ::= { gamQosCapabilities 4 }

gamQosCapabilitiesWredGroupMin OBJECT-TYPE
    SYNTAX      Unsigned32
    MAX-ACCESS  read-only
    STATUS      current
    DESCRIPTION
        "Minimum allowed WRED group number."
    ::= { gamQosCapabilities 5 }

gamQosCapabilitiesWredGroupMax OBJECT-TYPE
    SYNTAX      Unsigned32
    MAX-ACCESS  read-only
    STATUS      current
    DESCRIPTION
        "Maximum allowed WRED group number."
    ::= { gamQosCapabilities 6 }

gamQosCapabilitiesWredDplMin OBJECT-TYPE
    SYNTAX      GAMUnsigned8
    MAX-ACCESS  read-only
    STATUS      current
    DESCRIPTION
        "Minimum allowed WRED drop precedence level."
    ::= { gamQosCapabilities 7 }

gamQosCapabilitiesWredDplMax OBJECT-TYPE
    SYNTAX      GAMUnsigned8
    MAX-ACCESS  read-only
    STATUS      current
    DESCRIPTION
        "Maximum allowed WRED drop precedence level."
    ::= { gamQosCapabilities 8 }

gamQosCapabilitiesQceIdMin OBJECT-TYPE
    SYNTAX      Unsigned32
    MAX-ACCESS  read-only
    STATUS      current
    DESCRIPTION
        "Minimum allowed QCE Id."
    ::= { gamQosCapabilities 9 }

gamQosCapabilitiesQceIdMax OBJECT-TYPE
    SYNTAX      Unsigned32
    MAX-ACCESS  read-only
    STATUS      current
    DESCRIPTION
        "Maximum allowed QCE Id."
    ::= { gamQosCapabilities 10 }

gamQosCapabilitiesPortPolicerBitRateMin OBJECT-TYPE
    SYNTAX      Unsigned32
    MAX-ACCESS  read-only
    STATUS      current
    DESCRIPTION
        "Minimum supported bit rate in kbps for port policers using bit rate
         mode."
    ::= { gamQosCapabilities 11 }

gamQosCapabilitiesPortPolicerBitRateMax OBJECT-TYPE
    SYNTAX      Unsigned32
    MAX-ACCESS  read-only
    STATUS      current
    DESCRIPTION
        "Maximum supported bit rate in kbps for port policers using bit rate
         mode.
         
         If zero, the port policers does not support bit rate mode."
    ::= { gamQosCapabilities 12 }

gamQosCapabilitiesPortPolicerBitBurstMin OBJECT-TYPE
    SYNTAX      Unsigned32
    MAX-ACCESS  read-only
    STATUS      current
    DESCRIPTION
        "Minimum supported burst size in bytes for port policers using bit rate
         mode."
    ::= { gamQosCapabilities 13 }

gamQosCapabilitiesPortPolicerBitBurstMax OBJECT-TYPE
    SYNTAX      Unsigned32
    MAX-ACCESS  read-only
    STATUS      current
    DESCRIPTION
        "Maximum supported burst size in bytes for port policers using bit rate
         mode."
    ::= { gamQosCapabilities 14 }

gamQosCapabilitiesPortPolicerFrameRateMin OBJECT-TYPE
    SYNTAX      Unsigned32
    MAX-ACCESS  read-only
    STATUS      current
    DESCRIPTION
        "Minimum supported frame rate in fps for port policers using frame rate
         mode."
    ::= { gamQosCapabilities 15 }

gamQosCapabilitiesPortPolicerFrameRateMax OBJECT-TYPE
    SYNTAX      Unsigned32
    MAX-ACCESS  read-only
    STATUS      current
    DESCRIPTION
        "Maximum supported frame rate in fps for port policers using frame rate
         mode.
         
         If zero, the port policers does not support frame rate mode."
    ::= { gamQosCapabilities 16 }

gamQosCapabilitiesPortPolicerFrameBurstMin OBJECT-TYPE
    SYNTAX      Unsigned32
    MAX-ACCESS  read-only
    STATUS      current
    DESCRIPTION
        "Minimum supported burst size in frames for port policers using frame
         rate mode."
    ::= { gamQosCapabilities 17 }

gamQosCapabilitiesPortPolicerFrameBurstMax OBJECT-TYPE
    SYNTAX      Unsigned32
    MAX-ACCESS  read-only
    STATUS      current
    DESCRIPTION
        "Maximum supported burst size in frames for port policers using frame
         rate mode."
    ::= { gamQosCapabilities 18 }

gamQosCapabilitiesQueuePolicerBitRateMin OBJECT-TYPE
    SYNTAX      Unsigned32
    MAX-ACCESS  read-only
    STATUS      current
    DESCRIPTION
        "Minimum supported bit rate in kbps for queue policers using bit rate
         mode."
    ::= { gamQosCapabilities 19 }

gamQosCapabilitiesQueuePolicerBitRateMax OBJECT-TYPE
    SYNTAX      Unsigned32
    MAX-ACCESS  read-only
    STATUS      current
    DESCRIPTION
        "Maximum supported bit rate in kbps for queue policers using bit rate
         mode.
         
         If zero, the queue policers does not support bit rate mode."
    ::= { gamQosCapabilities 20 }

gamQosCapabilitiesQueuePolicerBitBurstMin OBJECT-TYPE
    SYNTAX      Unsigned32
    MAX-ACCESS  read-only
    STATUS      current
    DESCRIPTION
        "Minimum supported burst size in bytes for queue policers using bit rate
         mode."
    ::= { gamQosCapabilities 21 }

gamQosCapabilitiesQueuePolicerBitBurstMax OBJECT-TYPE
    SYNTAX      Unsigned32
    MAX-ACCESS  read-only
    STATUS      current
    DESCRIPTION
        "Maximum supported burst size in bytes for queue policers using bit rate
         mode."
    ::= { gamQosCapabilities 22 }

gamQosCapabilitiesQueuePolicerFrameRateMin OBJECT-TYPE
    SYNTAX      Unsigned32
    MAX-ACCESS  read-only
    STATUS      current
    DESCRIPTION
        "Minimum supported frame rate in fps for queue policers using frame rate
         mode."
    ::= { gamQosCapabilities 23 }

gamQosCapabilitiesQueuePolicerFrameRateMax OBJECT-TYPE
    SYNTAX      Unsigned32
    MAX-ACCESS  read-only
    STATUS      current
    DESCRIPTION
        "Maximum supported frame rate in fps for queue policers using frame rate
         mode.
         
         If zero, the port policers does not support frame rate mode."
    ::= { gamQosCapabilities 24 }

gamQosCapabilitiesQueuePolicerFrameBurstMin OBJECT-TYPE
    SYNTAX      Unsigned32
    MAX-ACCESS  read-only
    STATUS      current
    DESCRIPTION
        "Minimum supported burst size in frames for queue policers using frame
         rate mode."
    ::= { gamQosCapabilities 25 }

gamQosCapabilitiesQueuePolicerFrameBurstMax OBJECT-TYPE
    SYNTAX      Unsigned32
    MAX-ACCESS  read-only
    STATUS      current
    DESCRIPTION
        "Maximum supported burst size in frames for queue policers using frame
         rate mode."
    ::= { gamQosCapabilities 26 }

gamQosCapabilitiesPortShaperBitRateMin OBJECT-TYPE
    SYNTAX      Unsigned32
    MAX-ACCESS  read-only
    STATUS      current
    DESCRIPTION
        "Minimum supported bit rate in kbps for port shapers using bit rate
         mode."
    ::= { gamQosCapabilities 27 }

gamQosCapabilitiesPortShaperBitRateMax OBJECT-TYPE
    SYNTAX      Unsigned32
    MAX-ACCESS  read-only
    STATUS      current
    DESCRIPTION
        "Maximum supported bit rate in kbps for port shapers using bit rate
         mode.
         
         If zero, the port shapers does not support bit rate mode."
    ::= { gamQosCapabilities 28 }

gamQosCapabilitiesPortShaperBitBurstMin OBJECT-TYPE
    SYNTAX      Unsigned32
    MAX-ACCESS  read-only
    STATUS      current
    DESCRIPTION
        "Minimum supported burst size in bytes for port shapers using bit rate
         mode."
    ::= { gamQosCapabilities 29 }

gamQosCapabilitiesPortShaperBitBurstMax OBJECT-TYPE
    SYNTAX      Unsigned32
    MAX-ACCESS  read-only
    STATUS      current
    DESCRIPTION
        "Maximum supported burst size in bytes for port shapers using bit rate
         mode."
    ::= { gamQosCapabilities 30 }

gamQosCapabilitiesPortShaperFrameRateMin OBJECT-TYPE
    SYNTAX      Unsigned32
    MAX-ACCESS  read-only
    STATUS      current
    DESCRIPTION
        "Minimum supported frame rate in fps for port shapers using frame rate
         mode."
    ::= { gamQosCapabilities 31 }

gamQosCapabilitiesPortShaperFrameRateMax OBJECT-TYPE
    SYNTAX      Unsigned32
    MAX-ACCESS  read-only
    STATUS      current
    DESCRIPTION
        "Maximum supported frame rate in fps for port shapers using frame rate
         mode.
         
         If zero, the port shapers does not support frame rate mode."
    ::= { gamQosCapabilities 32 }

gamQosCapabilitiesPortShaperFrameBurstMin OBJECT-TYPE
    SYNTAX      Unsigned32
    MAX-ACCESS  read-only
    STATUS      current
    DESCRIPTION
        "Minimum supported burst size in frames for port shapers using frame
         rate mode."
    ::= { gamQosCapabilities 33 }

gamQosCapabilitiesPortShaperFrameBurstMax OBJECT-TYPE
    SYNTAX      Unsigned32
    MAX-ACCESS  read-only
    STATUS      current
    DESCRIPTION
        "Maximum supported burst size in frames for port shapers using frame
         rate mode."
    ::= { gamQosCapabilities 34 }

gamQosCapabilitiesQueueShaperBitRateMin OBJECT-TYPE
    SYNTAX      Unsigned32
    MAX-ACCESS  read-only
    STATUS      current
    DESCRIPTION
        "Minimum supported bit rate in kbps for queue shapers using bit rate
         mode."
    ::= { gamQosCapabilities 35 }

gamQosCapabilitiesQueueShaperBitRateMax OBJECT-TYPE
    SYNTAX      Unsigned32
    MAX-ACCESS  read-only
    STATUS      current
    DESCRIPTION
        "Maximum supported bit rate in kbps for queue shapers using bit rate
         mode.
         
         If zero, the queue shapers does not support bit rate mode."
    ::= { gamQosCapabilities 36 }

gamQosCapabilitiesQueueShaperBitBurstMin OBJECT-TYPE
    SYNTAX      Unsigned32
    MAX-ACCESS  read-only
    STATUS      current
    DESCRIPTION
        "Minimum supported burst size in bytes for queue shapers using bit rate
         mode."
    ::= { gamQosCapabilities 37 }

gamQosCapabilitiesQueueShaperBitBurstMax OBJECT-TYPE
    SYNTAX      Unsigned32
    MAX-ACCESS  read-only
    STATUS      current
    DESCRIPTION
        "Maximum supported burst size in bytes for queue shapers using bit rate
         mode."
    ::= { gamQosCapabilities 38 }

gamQosCapabilitiesQueueShaperFrameRateMin OBJECT-TYPE
    SYNTAX      Unsigned32
    MAX-ACCESS  read-only
    STATUS      current
    DESCRIPTION
        "Minimum supported frame rate in fps for queue shapers using frame rate
         mode."
    ::= { gamQosCapabilities 39 }

gamQosCapabilitiesQueueShaperFrameRateMax OBJECT-TYPE
    SYNTAX      Unsigned32
    MAX-ACCESS  read-only
    STATUS      current
    DESCRIPTION
        "Maximum supported frame rate in fps for queue shapers using frame rate
         mode.
         
         If zero, the port shapers does not support frame rate mode."
    ::= { gamQosCapabilities 40 }

gamQosCapabilitiesQueueShaperFrameBurstMin OBJECT-TYPE
    SYNTAX      Unsigned32
    MAX-ACCESS  read-only
    STATUS      current
    DESCRIPTION
        "Minimum supported burst size in frames for queue shapers using frame
         rate mode."
    ::= { gamQosCapabilities 41 }

gamQosCapabilitiesQueueShaperFrameBurstMax OBJECT-TYPE
    SYNTAX      Unsigned32
    MAX-ACCESS  read-only
    STATUS      current
    DESCRIPTION
        "Maximum supported burst size in frames for queue shapers using frame
         rate mode."
    ::= { gamQosCapabilities 42 }

gamQosCapabilitiesGlobalStormBitRateMin OBJECT-TYPE
    SYNTAX      Unsigned32
    MAX-ACCESS  read-only
    STATUS      current
    DESCRIPTION
        "Minimum supported bit rate in kbps for global storm policers using bit
         rate mode."
    ::= { gamQosCapabilities 43 }

gamQosCapabilitiesGlobalStormBitRateMax OBJECT-TYPE
    SYNTAX      Unsigned32
    MAX-ACCESS  read-only
    STATUS      current
    DESCRIPTION
        "Maximum supported bit rate in kbps for global storm policers using bit
         rate mode.
         
         If zero, the global storm policers does not support bit rate mode."
    ::= { gamQosCapabilities 44 }

gamQosCapabilitiesGlobalStormBitBurstMin OBJECT-TYPE
    SYNTAX      Unsigned32
    MAX-ACCESS  read-only
    STATUS      current
    DESCRIPTION
        "Minimum supported burst size in bytes for global storm policers using
         bit rate mode."
    ::= { gamQosCapabilities 45 }

gamQosCapabilitiesGlobalStormBitBurstMax OBJECT-TYPE
    SYNTAX      Unsigned32
    MAX-ACCESS  read-only
    STATUS      current
    DESCRIPTION
        "Maximum supported burst size in bytes for global storm policers using
         bit rate mode."
    ::= { gamQosCapabilities 46 }

gamQosCapabilitiesGlobalStormFrameRateMin OBJECT-TYPE
    SYNTAX      Unsigned32
    MAX-ACCESS  read-only
    STATUS      current
    DESCRIPTION
        "Minimum supported frame rate in fps for global storm policers using
         frame rate mode."
    ::= { gamQosCapabilities 47 }

gamQosCapabilitiesGlobalStormFrameRateMax OBJECT-TYPE
    SYNTAX      Unsigned32
    MAX-ACCESS  read-only
    STATUS      current
    DESCRIPTION
        "Maximum supported frame rate in fps for global storm policers using
         frame rate mode.
         
         If zero, the global storm policers does not support frame rate mode."
    ::= { gamQosCapabilities 48 }

gamQosCapabilitiesGlobalStormFrameBurstMin OBJECT-TYPE
    SYNTAX      Unsigned32
    MAX-ACCESS  read-only
    STATUS      current
    DESCRIPTION
        "Minimum supported burst size in frames for global storm policers using
         frame rate mode."
    ::= { gamQosCapabilities 49 }

gamQosCapabilitiesGlobalStormFrameBurstMax OBJECT-TYPE
    SYNTAX      Unsigned32
    MAX-ACCESS  read-only
    STATUS      current
    DESCRIPTION
        "Maximum supported burst size in frames for global storm policers using
         frame rate mode."
    ::= { gamQosCapabilities 50 }

gamQosCapabilitiesPortStormBitRateMin OBJECT-TYPE
    SYNTAX      Unsigned32
    MAX-ACCESS  read-only
    STATUS      current
    DESCRIPTION
        "Minimum supported bit rate in kbps for port storm policers using bit
         rate mode."
    ::= { gamQosCapabilities 51 }

gamQosCapabilitiesPortStormBitRateMax OBJECT-TYPE
    SYNTAX      Unsigned32
    MAX-ACCESS  read-only
    STATUS      current
    DESCRIPTION
        "Maximum supported bit rate in kbps for port storm policers using bit
         rate mode.
         
         If zero, the port storm policers does not support bit rate mode."
    ::= { gamQosCapabilities 52 }

gamQosCapabilitiesPortStormBitBurstMin OBJECT-TYPE
    SYNTAX      Unsigned32
    MAX-ACCESS  read-only
    STATUS      current
    DESCRIPTION
        "Minimum supported burst size in bytes for port storm policers using bit
         rate mode."
    ::= { gamQosCapabilities 53 }

gamQosCapabilitiesPortStormBitBurstMax OBJECT-TYPE
    SYNTAX      Unsigned32
    MAX-ACCESS  read-only
    STATUS      current
    DESCRIPTION
        "Maximum supported burst size in bytes for port storm policers using bit
         rate mode."
    ::= { gamQosCapabilities 54 }

gamQosCapabilitiesPortStormFrameRateMin OBJECT-TYPE
    SYNTAX      Unsigned32
    MAX-ACCESS  read-only
    STATUS      current
    DESCRIPTION
        "Minimum supported frame rate in fps for port storm policers using frame
         rate mode."
    ::= { gamQosCapabilities 55 }

gamQosCapabilitiesPortStormFrameRateMax OBJECT-TYPE
    SYNTAX      Unsigned32
    MAX-ACCESS  read-only
    STATUS      current
    DESCRIPTION
        "Maximum supported frame rate in fps for port storm policers using frame
         rate mode.
         
         If zero, the port storm policers does not support frame rate mode."
    ::= { gamQosCapabilities 56 }

gamQosCapabilitiesPortStormFrameBurstMin OBJECT-TYPE
    SYNTAX      Unsigned32
    MAX-ACCESS  read-only
    STATUS      current
    DESCRIPTION
        "Minimum supported burst size in frames for port storm policers using
         frame rate mode."
    ::= { gamQosCapabilities 57 }

gamQosCapabilitiesPortStormFrameBurstMax OBJECT-TYPE
    SYNTAX      Unsigned32
    MAX-ACCESS  read-only
    STATUS      current
    DESCRIPTION
        "Maximum supported burst size in frames for port storm policers using
         frame rate mode."
    ::= { gamQosCapabilities 58 }

gamQosCapabilitiesIngressMapIdMin OBJECT-TYPE
    SYNTAX      Unsigned32
    MAX-ACCESS  read-only
    STATUS      current
    DESCRIPTION
        "Minimum supported index of Ingress map."
    ::= { gamQosCapabilities 59 }

gamQosCapabilitiesIngressMapIdMax OBJECT-TYPE
    SYNTAX      Unsigned32
    MAX-ACCESS  read-only
    STATUS      current
    DESCRIPTION
        "Maximum supported index of Ingress map."
    ::= { gamQosCapabilities 60 }

gamQosCapabilitiesEgressMapIdMin OBJECT-TYPE
    SYNTAX      Unsigned32
    MAX-ACCESS  read-only
    STATUS      current
    DESCRIPTION
        "Minimum supported index of Egress map."
    ::= { gamQosCapabilities 61 }

gamQosCapabilitiesEgressMapIdMax OBJECT-TYPE
    SYNTAX      Unsigned32
    MAX-ACCESS  read-only
    STATUS      current
    DESCRIPTION
        "Maximum supported index of Egress map."
    ::= { gamQosCapabilities 62 }

gamQosCapabilitiesCosIdMin OBJECT-TYPE
    SYNTAX      Unsigned32
    MAX-ACCESS  read-only
    STATUS      current
    DESCRIPTION
        "Minimum allowed COSID value."
    ::= { gamQosCapabilities 63 }

gamQosCapabilitiesCosIdMax OBJECT-TYPE
    SYNTAX      Unsigned32
    MAX-ACCESS  read-only
    STATUS      current
    DESCRIPTION
        "Maximum allowed COSID value."
    ::= { gamQosCapabilities 64 }

gamQosCapabilitiesQbvGclLenMax OBJECT-TYPE
    SYNTAX      Unsigned32
    MAX-ACCESS  read-only
    STATUS      current
    DESCRIPTION
        "Maximum supported length of gate control list."
    ::= { gamQosCapabilities 65 }

gamQosCapabilitiesDwrrCountMask OBJECT-TYPE
    SYNTAX      Unsigned32
    MAX-ACCESS  read-only
    STATUS      current
    DESCRIPTION
        "A bitmask used to show allowed values of DwrrCount (zero is always
         allowed).
         
         Example:
         
         00100000 (0x20): Allowed values are 0 and 6
         
         11111110 (0xFE): Allowed values are 0 and 2..8"
    ::= { gamQosCapabilities 101 }

gamQosCapabilitiesHasGlobalStormPolicers OBJECT-TYPE
    SYNTAX      TruthValue
    MAX-ACCESS  read-only
    STATUS      current
    DESCRIPTION
        "If true, the platform supports global storm policers."
    ::= { gamQosCapabilities 201 }

gamQosCapabilitiesHasPortStormPolicers OBJECT-TYPE
    SYNTAX      TruthValue
    MAX-ACCESS  read-only
    STATUS      current
    DESCRIPTION
        "If true, the platform supports per port storm policers."
    ::= { gamQosCapabilities 202 }

gamQosCapabilitiesHasPortQueuePolicers OBJECT-TYPE
    SYNTAX      TruthValue
    MAX-ACCESS  read-only
    STATUS      current
    DESCRIPTION
        "If true, the platform supports per port queue policers."
    ::= { gamQosCapabilities 203 }

gamQosCapabilitiesHasWredV1 OBJECT-TYPE
    SYNTAX      TruthValue
    MAX-ACCESS  read-only
    STATUS      current
    DESCRIPTION
        "If true, the platform supports WRED version 1."
    ::= { gamQosCapabilities 204 }

gamQosCapabilitiesHasWredV2 OBJECT-TYPE
    SYNTAX      TruthValue
    MAX-ACCESS  read-only
    STATUS      current
    DESCRIPTION
        "If true, the platform supports WRED version 2."
    ::= { gamQosCapabilities 205 }

gamQosCapabilitiesHasFixedTagCosMap OBJECT-TYPE
    SYNTAX      TruthValue
    MAX-ACCESS  read-only
    STATUS      current
    DESCRIPTION
        "If true, the platform supports fixed tag to cos mapping only."
    ::= { gamQosCapabilities 206 }

gamQosCapabilitiesHasTagClassification OBJECT-TYPE
    SYNTAX      TruthValue
    MAX-ACCESS  read-only
    STATUS      current
    DESCRIPTION
        "If true, the platform supports using VLAN tag for classification."
    ::= { gamQosCapabilities 207 }

gamQosCapabilitiesHasTagRemarking OBJECT-TYPE
    SYNTAX      TruthValue
    MAX-ACCESS  read-only
    STATUS      current
    DESCRIPTION
        "If true, the platform supports VLAN tag remarking."
    ::= { gamQosCapabilities 208 }

gamQosCapabilitiesHasDscp OBJECT-TYPE
    SYNTAX      TruthValue
    MAX-ACCESS  read-only
    STATUS      current
    DESCRIPTION
        "If true, the platform supports DSCP translation and remarking."
    ::= { gamQosCapabilities 209 }

gamQosCapabilitiesHasDscpDplClassification OBJECT-TYPE
    SYNTAX      TruthValue
    MAX-ACCESS  read-only
    STATUS      current
    DESCRIPTION
        "If true, the platform supports DPL based DSCP classification."
    ::= { gamQosCapabilities 210 }

gamQosCapabilitiesHasDscpDplRemarking OBJECT-TYPE
    SYNTAX      TruthValue
    MAX-ACCESS  read-only
    STATUS      current
    DESCRIPTION
        "If true, the platform supports DPL based DSCP remarking."
    ::= { gamQosCapabilities 211 }

gamQosCapabilitiesHasPortPolicersFc OBJECT-TYPE
    SYNTAX      TruthValue
    MAX-ACCESS  read-only
    STATUS      current
    DESCRIPTION
        "If true, the platform supports flow control in port policers."
    ::= { gamQosCapabilities 212 }

gamQosCapabilitiesHasQueuePolicersFc OBJECT-TYPE
    SYNTAX      TruthValue
    MAX-ACCESS  read-only
    STATUS      current
    DESCRIPTION
        "If true, the platform supports flow control in queue policers."
    ::= { gamQosCapabilities 213 }

gamQosCapabilitiesHasPortShapersDlb OBJECT-TYPE
    SYNTAX      TruthValue
    MAX-ACCESS  read-only
    STATUS      current
    DESCRIPTION
        "If true, the platform supports dual leaky bucket egress port shapers."
    ::= { gamQosCapabilities 214 }

gamQosCapabilitiesHasQueueShapersDlb OBJECT-TYPE
    SYNTAX      TruthValue
    MAX-ACCESS  read-only
    STATUS      current
    DESCRIPTION
        "If true, the platform supports dual leaky bucket egress queue shapers."
    ::= { gamQosCapabilities 215 }

gamQosCapabilitiesHasQueueShapersExcess OBJECT-TYPE
    SYNTAX      TruthValue
    MAX-ACCESS  read-only
    STATUS      current
    DESCRIPTION
        "If true, the platform supports excess bandwidth in egress queue
         shapers."
    ::= { gamQosCapabilities 216 }

gamQosCapabilitiesHasWredV3 OBJECT-TYPE
    SYNTAX      TruthValue
    MAX-ACCESS  read-only
    STATUS      current
    DESCRIPTION
        "If true, the platform supports WRED version 3."
    ::= { gamQosCapabilities 217 }

gamQosCapabilitiesHasQueueShapersCredit OBJECT-TYPE
    SYNTAX      TruthValue
    MAX-ACCESS  read-only
    STATUS      current
    DESCRIPTION
        "If true, the platform supports bursty traffic in egress queue shapers."
    ::= { gamQosCapabilities 218 }

gamQosCapabilitiesHasQueueCutThrough OBJECT-TYPE
    SYNTAX      TruthValue
    MAX-ACCESS  read-only
    STATUS      current
    DESCRIPTION
        "If true, the platform supports cut through in egress queue."
    ::= { gamQosCapabilities 219 }

gamQosCapabilitiesHasQueueFramePreemption OBJECT-TYPE
    SYNTAX      TruthValue
    MAX-ACCESS  read-only
    STATUS      current
    DESCRIPTION
        "If true, the platform supports frame preemption in egress queue."
    ::= { gamQosCapabilities 220 }

gamQosCapabilitiesHasQce OBJECT-TYPE
    SYNTAX      TruthValue
    MAX-ACCESS  read-only
    STATUS      current
    DESCRIPTION
        "If true, the platform supports QCEs."
    ::= { gamQosCapabilities 301 }

gamQosCapabilitiesHasQceAddressMode OBJECT-TYPE
    SYNTAX      TruthValue
    MAX-ACCESS  read-only
    STATUS      current
    DESCRIPTION
        "If true, the platform supports QCE address mode."
    ::= { gamQosCapabilities 302 }

gamQosCapabilitiesHasQceKeyType OBJECT-TYPE
    SYNTAX      TruthValue
    MAX-ACCESS  read-only
    STATUS      current
    DESCRIPTION
        "If true, the platform supports QCE key type."
    ::= { gamQosCapabilities 303 }

gamQosCapabilitiesHasQceMacOui OBJECT-TYPE
    SYNTAX      TruthValue
    MAX-ACCESS  read-only
    STATUS      current
    DESCRIPTION
        "If true, the platform supports QCE MAC OUI part only (24 most
         significant bits)."
    ::= { gamQosCapabilities 304 }

gamQosCapabilitiesHasQceDmac OBJECT-TYPE
    SYNTAX      TruthValue
    MAX-ACCESS  read-only
    STATUS      current
    DESCRIPTION
        "If true, the platform supports QCE destination MAC keys."
    ::= { gamQosCapabilities 305 }

gamQosCapabilitiesHasQceDip OBJECT-TYPE
    SYNTAX      TruthValue
    MAX-ACCESS  read-only
    STATUS      current
    DESCRIPTION
        "If true, the platform supports QCE destination IP keys."
    ::= { gamQosCapabilities 306 }

gamQosCapabilitiesHasQceCTag OBJECT-TYPE
    SYNTAX      TruthValue
    MAX-ACCESS  read-only
    STATUS      current
    DESCRIPTION
        "If true, the platform supports QCE VLAN C-TAG keys."
    ::= { gamQosCapabilities 307 }

gamQosCapabilitiesHasQceSTag OBJECT-TYPE
    SYNTAX      TruthValue
    MAX-ACCESS  read-only
    STATUS      current
    DESCRIPTION
        "If true, the platform supports QCE VLAN S-TAG keys."
    ::= { gamQosCapabilities 308 }

gamQosCapabilitiesHasQceInnerTag OBJECT-TYPE
    SYNTAX      TruthValue
    MAX-ACCESS  read-only
    STATUS      current
    DESCRIPTION
        "If true, the platform supports QCE inner VLAN tag keys."
    ::= { gamQosCapabilities 309 }

gamQosCapabilitiesHasQceActionPcpDei OBJECT-TYPE
    SYNTAX      TruthValue
    MAX-ACCESS  read-only
    STATUS      current
    DESCRIPTION
        "If true, the platform supports QCE PCP and DEI actions."
    ::= { gamQosCapabilities 310 }

gamQosCapabilitiesHasQceActionPolicy OBJECT-TYPE
    SYNTAX      TruthValue
    MAX-ACCESS  read-only
    STATUS      current
    DESCRIPTION
        "If true, the platform supports QCE policy actions."
    ::= { gamQosCapabilities 311 }

gamQosCapabilitiesHasShapersRt OBJECT-TYPE
    SYNTAX      TruthValue
    MAX-ACCESS  read-only
    STATUS      current
    DESCRIPTION
        "If true, the platform supports rate-type configurable egress shapers."
    ::= { gamQosCapabilities 312 }

gamQosCapabilitiesHasQceActionMap OBJECT-TYPE
    SYNTAX      TruthValue
    MAX-ACCESS  read-only
    STATUS      current
    DESCRIPTION
        "If true, the platform supports QCE ingress map actions."
    ::= { gamQosCapabilities 313 }

gamQosCapabilitiesHasIngressMap OBJECT-TYPE
    SYNTAX      TruthValue
    MAX-ACCESS  read-only
    STATUS      current
    DESCRIPTION
        "If true, the platform supports Ingress mapping tables"
    ::= { gamQosCapabilities 314 }

gamQosCapabilitiesHasEgressMap OBJECT-TYPE
    SYNTAX      TruthValue
    MAX-ACCESS  read-only
    STATUS      current
    DESCRIPTION
        "If true, the platform supports Egress mapping tables"
    ::= { gamQosCapabilities 315 }

gamQosCapabilitiesHasWred2orWredw3 OBJECT-TYPE
    SYNTAX      TruthValue
    MAX-ACCESS  read-only
    STATUS      current
    DESCRIPTION
        "This object is only valid if qosCapabilitiesHasWredV2 or
         qosCapabilitiesHasWredV3 is true."
    ::= { gamQosCapabilities 316 }

gamQosCapabilitiesHasDscpDp2 OBJECT-TYPE
    SYNTAX      TruthValue
    MAX-ACCESS  read-only
    STATUS      current
    DESCRIPTION
        "This object is only valid if qosCapabilitiesHasDscpDplClassification is
         true and qosCapabilitiesDplMax is greater than 1."
    ::= { gamQosCapabilities 317 }

gamQosCapabilitiesHasDscpDp3 OBJECT-TYPE
    SYNTAX      TruthValue
    MAX-ACCESS  read-only
    STATUS      current
    DESCRIPTION
        "This object is only valid if qosCapabilitiesHasDscpDplClassification is
         true and qosCapabilitiesDplMax is greater than 2."
    ::= { gamQosCapabilities 318 }

gamQosCapabilitiesHasDefaultPcpAndDei OBJECT-TYPE
    SYNTAX      TruthValue
    MAX-ACCESS  read-only
    STATUS      current
    DESCRIPTION
        "This object is only valid if qosCapabilitiesHasDefaultPcpAndDei is
         true."
    ::= { gamQosCapabilities 319 }

gamQosCapabilitiesHasTrustTag OBJECT-TYPE
    SYNTAX      TruthValue
    MAX-ACCESS  read-only
    STATUS      current
    DESCRIPTION
        "This object is only valid if qosCapabilitiesHasFixedTagCosMap is false
         and qosCapabilitiesHasTagClassification is true."
    ::= { gamQosCapabilities 320 }

gamQosCapabilitiesHasCosIdClassification OBJECT-TYPE
    SYNTAX      TruthValue
    MAX-ACCESS  read-only
    STATUS      current
    DESCRIPTION
        "If true, the platform supports COSID classification."
    ::= { gamQosCapabilities 321 }

gamQosCapabilitiesHasQbv OBJECT-TYPE
    SYNTAX      TruthValue
    MAX-ACCESS  read-only
    STATUS      current
    DESCRIPTION
        "If true, the platform supports Time Aware Shaper."
    ::= { gamQosCapabilities 322 }

gamQosCapabilitiesHasWred OBJECT-TYPE
    SYNTAX      TruthValue
    MAX-ACCESS  read-only
    STATUS      current
    DESCRIPTION
        "This object is only valid if the platform supports any form of Wred."
    ::= { gamQosCapabilities 323 }

gamQosCapabilitiesHasPsfp OBJECT-TYPE
    SYNTAX      TruthValue
    MAX-ACCESS  read-only
    STATUS      current
    DESCRIPTION
        "If true, the platform supports Per stream Filtering and Policing."
    ::= { gamQosCapabilities 324 }

gamQosConfig OBJECT IDENTIFIER
    ::= { gamQosMibObjects 2 }

gamQosConfigGlobals OBJECT IDENTIFIER
    ::= { gamQosConfig 1 }

gamQosConfigGlobalsStormPolicers OBJECT IDENTIFIER
    ::= { gamQosConfigGlobals 1 }

gamQosConfigGlobalsStormPolicersUnicast OBJECT IDENTIFIER
    ::= { gamQosConfigGlobalsStormPolicers 1 }

gamQosConfigGlobalsStormPolicersUnicastEnable OBJECT-TYPE
    SYNTAX      TruthValue
    MAX-ACCESS  read-write
    STATUS      current
    DESCRIPTION
        "If true, the storm policer is enabled.
         
         
         
         This object is only available if the capability object
         'gamQosCapabilitiesHasGlobalStormPolicers' is True."
    ::= { gamQosConfigGlobalsStormPolicersUnicast 1 }

gamQosConfigGlobalsStormPolicersUnicastRate OBJECT-TYPE
    SYNTAX      Unsigned32
    MAX-ACCESS  read-write
    STATUS      current
    DESCRIPTION
        "Configure the storm policer rate.
         
         Valid range is from the smallest value of
         qosCapabilitiesGlobalStormBitRateMin and
         qosCapabilitiesGlobalStormFrameRateMin to the largest value of
         qosCapabilitiesGlobalStormBitRateMax and
         qosCapabilitiesGlobalStormFrameRateMax.
         
         
         
         This object is only available if the capability object
         'gamQosCapabilitiesHasGlobalStormPolicers' is True."
    ::= { gamQosConfigGlobalsStormPolicersUnicast 2 }

gamQosConfigGlobalsStormPolicersUnicastFrameRate OBJECT-TYPE
    SYNTAX      TruthValue
    MAX-ACCESS  read-write
    STATUS      current
    DESCRIPTION
        "If true, the rate is measured in fps instead of kbps.
         
         fps (FrameRate == TRUE) is only valid if
         qosCapabilitiesGlobalStormFrameRateMax is non-zero.
         
         kbps (FrameRate == FALSE) is only valid if
         qosCapabilitiesGlobalStormBitRateMax is non-zero.
         
         
         
         This object is only available if the capability object
         'gamQosCapabilitiesHasGlobalStormPolicers' is True."
    ::= { gamQosConfigGlobalsStormPolicersUnicast 3 }

gamQosConfigGlobalsStormPolicersMulticast OBJECT IDENTIFIER
    ::= { gamQosConfigGlobalsStormPolicers 2 }

gamQosConfigGlobalsStormPolicersMulticastEnable OBJECT-TYPE
    SYNTAX      TruthValue
    MAX-ACCESS  read-write
    STATUS      current
    DESCRIPTION
        "If true, the storm policer is enabled.
         
         
         
         This object is only available if the capability object
         'gamQosCapabilitiesHasGlobalStormPolicers' is True."
    ::= { gamQosConfigGlobalsStormPolicersMulticast 1 }

gamQosConfigGlobalsStormPolicersMulticastRate OBJECT-TYPE
    SYNTAX      Unsigned32
    MAX-ACCESS  read-write
    STATUS      current
    DESCRIPTION
        "Configure the storm policer rate.
         
         Valid range is from the smallest value of
         qosCapabilitiesGlobalStormBitRateMin and
         qosCapabilitiesGlobalStormFrameRateMin to the largest value of
         qosCapabilitiesGlobalStormBitRateMax and
         qosCapabilitiesGlobalStormFrameRateMax.
         
         
         
         This object is only available if the capability object
         'gamQosCapabilitiesHasGlobalStormPolicers' is True."
    ::= { gamQosConfigGlobalsStormPolicersMulticast 2 }

gamQosConfigGlobalsStormPolicersMulticastFrameRate OBJECT-TYPE
    SYNTAX      TruthValue
    MAX-ACCESS  read-write
    STATUS      current
    DESCRIPTION
        "If true, the rate is measured in fps instead of kbps.
         
         fps (FrameRate == TRUE) is only valid if
         qosCapabilitiesGlobalStormFrameRateMax is non-zero.
         
         kbps (FrameRate == FALSE) is only valid if
         qosCapabilitiesGlobalStormBitRateMax is non-zero.
         
         
         
         This object is only available if the capability object
         'gamQosCapabilitiesHasGlobalStormPolicers' is True."
    ::= { gamQosConfigGlobalsStormPolicersMulticast 3 }

gamQosConfigGlobalsStormPolicersBroadcast OBJECT IDENTIFIER
    ::= { gamQosConfigGlobalsStormPolicers 3 }

gamQosConfigGlobalsStormPolicersBroadcastEnable OBJECT-TYPE
    SYNTAX      TruthValue
    MAX-ACCESS  read-write
    STATUS      current
    DESCRIPTION
        "If true, the storm policer is enabled.
         
         
         
         This object is only available if the capability object
         'gamQosCapabilitiesHasGlobalStormPolicers' is True."
    ::= { gamQosConfigGlobalsStormPolicersBroadcast 1 }

gamQosConfigGlobalsStormPolicersBroadcastRate OBJECT-TYPE
    SYNTAX      Unsigned32
    MAX-ACCESS  read-write
    STATUS      current
    DESCRIPTION
        "Configure the storm policer rate.
         
         Valid range is from the smallest value of
         qosCapabilitiesGlobalStormBitRateMin and
         qosCapabilitiesGlobalStormFrameRateMin to the largest value of
         qosCapabilitiesGlobalStormBitRateMax and
         qosCapabilitiesGlobalStormFrameRateMax.
         
         
         
         This object is only available if the capability object
         'gamQosCapabilitiesHasGlobalStormPolicers' is True."
    ::= { gamQosConfigGlobalsStormPolicersBroadcast 2 }

gamQosConfigGlobalsStormPolicersBroadcastFrameRate OBJECT-TYPE
    SYNTAX      TruthValue
    MAX-ACCESS  read-write
    STATUS      current
    DESCRIPTION
        "If true, the rate is measured in fps instead of kbps.
         
         fps (FrameRate == TRUE) is only valid if
         qosCapabilitiesGlobalStormFrameRateMax is non-zero.
         
         kbps (FrameRate == FALSE) is only valid if
         qosCapabilitiesGlobalStormBitRateMax is non-zero.
         
         
         
         This object is only available if the capability object
         'gamQosCapabilitiesHasGlobalStormPolicers' is True."
    ::= { gamQosConfigGlobalsStormPolicersBroadcast 3 }

gamQosConfigGlobalsWredTable OBJECT-TYPE
    SYNTAX      SEQUENCE OF GAMQosConfigGlobalsWredEntry
    MAX-ACCESS  not-accessible
    STATUS      current
    DESCRIPTION
        "This table contains the configuration of WRED (Weighted Random Early
         Discard).
         
         This is an optional table and is only present if qosCapabilitiesHasWred
         is true."
    ::= { gamQosConfigGlobals 2 }

gamQosConfigGlobalsWredEntry OBJECT-TYPE
    SYNTAX      GAMQosConfigGlobalsWredEntry
    MAX-ACCESS  not-accessible
    STATUS      current
    DESCRIPTION
        "Each row contains the configuration for a specific WRED profile"
    INDEX       { gamQosConfigGlobalsWredGroup,
                  gamQosConfigGlobalsWredQueue,
                  gamQosConfigGlobalsWredDpl }
    ::= { gamQosConfigGlobalsWredTable 1 }

GAMQosConfigGlobalsWredEntry ::= SEQUENCE {
    gamQosConfigGlobalsWredGroup             Integer32,
    gamQosConfigGlobalsWredQueue             Integer32,
    gamQosConfigGlobalsWredDpl               Integer32,
    gamQosConfigGlobalsWredEnable            TruthValue,
    gamQosConfigGlobalsWredMinimumFillLevel  GAMPercent,
    gamQosConfigGlobalsWredMaximum           GAMPercent,
    gamQosConfigGlobalsWredMaxSelector       GAMQosWredMaxSelector,
    gamQosConfigGlobalsWredMaximumDp1        GAMPercent,
    gamQosConfigGlobalsWredMaximumDp2        GAMPercent,
    gamQosConfigGlobalsWredMaximumDp3        GAMPercent
}

gamQosConfigGlobalsWredGroup OBJECT-TYPE
    SYNTAX      Integer32 (1..3)
    MAX-ACCESS  accessible-for-notify
    STATUS      current
    DESCRIPTION
        "WRED group index.
         
         This object is only available if the capability object
         'gamQosCapabilitiesHasWred' is True."
    ::= { gamQosConfigGlobalsWredEntry 1 }

gamQosConfigGlobalsWredQueue OBJECT-TYPE
    SYNTAX      Integer32 (0..7)
    MAX-ACCESS  accessible-for-notify
    STATUS      current
    DESCRIPTION
        "Queue index.
         
         This object is only available if the capability object
         'gamQosCapabilitiesHasWred' is True."
    ::= { gamQosConfigGlobalsWredEntry 2 }

gamQosConfigGlobalsWredDpl OBJECT-TYPE
    SYNTAX      Integer32 (0..3)
    MAX-ACCESS  accessible-for-notify
    STATUS      current
    DESCRIPTION
        "DPL index.
         
         This object is only available if the capability object
         'gamQosCapabilitiesHasWred' is True."
    ::= { gamQosConfigGlobalsWredEntry 3 }

gamQosConfigGlobalsWredEnable OBJECT-TYPE
    SYNTAX      TruthValue
    MAX-ACCESS  read-write
    STATUS      current
    DESCRIPTION
        "If true, RED is enabled for this queue.
         
         This object is only available if the capability object
         'gamQosCapabilitiesHasWred' is True."
    ::= { gamQosConfigGlobalsWredEntry 4 }

gamQosConfigGlobalsWredMinimumFillLevel OBJECT-TYPE
    SYNTAX      GAMPercent
    MAX-ACCESS  read-write
    STATUS      current
    DESCRIPTION
        "Controls the lower RED fill level threshold in percent of the whole
         queue.
         
         If the queue filling level is below this threshold, the drop
         probability is zero.
         
         Valid range is 0-100.
         
         This object is only available if the capability object
         'gamQosCapabilitiesHasWred' is True."
    ::= { gamQosConfigGlobalsWredEntry 5 }

gamQosConfigGlobalsWredMaximum OBJECT-TYPE
    SYNTAX      GAMPercent
    MAX-ACCESS  read-write
    STATUS      current
    DESCRIPTION
        "Controls the upper RED drop probability or fill level threshold for
         frames marked with Drop Precedence Level 1 (yellow frames).
         
         Valid range is 1-100.
         
         
         
         This object is only available if the capability object
         'gamQosCapabilitiesHasWred2orWredw3' is True."
    ::= { gamQosConfigGlobalsWredEntry 6 }

gamQosConfigGlobalsWredMaxSelector OBJECT-TYPE
    SYNTAX      GAMQosWredMaxSelector
    MAX-ACCESS  read-write
    STATUS      current
    DESCRIPTION
        "Selects whether 'Maximum' controls 'Maximum Drop Probability' or
         'Maximum Fill Level'.
         
         
         
         This object is only available if the capability object
         'gamQosCapabilitiesHasWred2orWredw3' is True."
    ::= { gamQosConfigGlobalsWredEntry 7 }

gamQosConfigGlobalsWredMaximumDp1 OBJECT-TYPE
    SYNTAX      GAMPercent
    MAX-ACCESS  read-write
    STATUS      current
    DESCRIPTION
        "Controls the upper RED drop probability for frames marked with Drop
         Precedence Level 1 (yellow frames).
         
         Valid range is 0-100.
         
         
         
         This object is only available if the capability object
         'gamQosCapabilitiesHasWredV1' is True."
    ::= { gamQosConfigGlobalsWredEntry 8 }

gamQosConfigGlobalsWredMaximumDp2 OBJECT-TYPE
    SYNTAX      GAMPercent
    MAX-ACCESS  read-write
    STATUS      current
    DESCRIPTION
        "Controls the upper RED drop probability for frames marked with Drop
         Precedence Level 2 (yellow frames).
         
         Valid range is 0-100.
         
         
         
         This object is only available if the capability object
         'gamQosCapabilitiesHasWredV1' is True."
    ::= { gamQosConfigGlobalsWredEntry 9 }

gamQosConfigGlobalsWredMaximumDp3 OBJECT-TYPE
    SYNTAX      GAMPercent
    MAX-ACCESS  read-write
    STATUS      current
    DESCRIPTION
        "Controls the upper RED drop probability for frames marked with Drop
         Precedence Level 3 (yellow frames).
         
         Valid range is 0-100.
         
         
         
         This object is only available if the capability object
         'gamQosCapabilitiesHasWredV1' is True."
    ::= { gamQosConfigGlobalsWredEntry 10 }

gamQosConfigGlobalsDscpTable OBJECT-TYPE
    SYNTAX      SEQUENCE OF GAMQosConfigGlobalsDscpEntry
    MAX-ACCESS  not-accessible
    STATUS      current
    DESCRIPTION
        "This table has 64 entries, one for each DSCP value.
         
         This is an optional table and is only present if qosCapabilitiesHasDscp
         is true."
    ::= { gamQosConfigGlobals 3 }

gamQosConfigGlobalsDscpEntry OBJECT-TYPE
    SYNTAX      GAMQosConfigGlobalsDscpEntry
    MAX-ACCESS  not-accessible
    STATUS      current
    DESCRIPTION
        "Each row contains the configuration for a specific DSCP"
    INDEX       { gamQosConfigGlobalsDscpDscp }
    ::= { gamQosConfigGlobalsDscpTable 1 }

GAMQosConfigGlobalsDscpEntry ::= SEQUENCE {
    gamQosConfigGlobalsDscpDscp                  Dscp,
    gamQosConfigGlobalsDscpTrust                 TruthValue,
    gamQosConfigGlobalsDscpCos                   Unsigned32,
    gamQosConfigGlobalsDscpDpl                   GAMUnsigned8,
    gamQosConfigGlobalsDscpIngressTranslation    Dscp,
    gamQosConfigGlobalsDscpClassify              TruthValue,
    gamQosConfigGlobalsDscpEgressTranslation     Dscp,
    gamQosConfigGlobalsDscpEgressTranslationDp1  Dscp
}

gamQosConfigGlobalsDscpDscp OBJECT-TYPE
    SYNTAX      Dscp
    MAX-ACCESS  accessible-for-notify
    STATUS      current
    DESCRIPTION
        "DSCP index.
         
         This object is only available if the capability object
         'gamQosCapabilitiesHasDscp' is True."
    ::= { gamQosConfigGlobalsDscpEntry 1 }

gamQosConfigGlobalsDscpTrust OBJECT-TYPE
    SYNTAX      TruthValue
    MAX-ACCESS  read-write
    STATUS      current
    DESCRIPTION
        "If true, this DSCP value is trusted. Packets arriving on interfaces
         where 'TrustDscp' is enabled will be classified to the corresponding
         CoS and DPL in this table.
         
         This object is only available if the capability object
         'gamQosCapabilitiesHasDscp' is True."
    ::= { gamQosConfigGlobalsDscpEntry 2 }

gamQosConfigGlobalsDscpCos OBJECT-TYPE
    SYNTAX      Unsigned32
    MAX-ACCESS  read-write
    STATUS      current
    DESCRIPTION
        "The CoS value which the DSCP value maps to.
         
         Valid range is qosCapabilitiesClassMin-qosCapabilitiesClassMax.
         
         This object is only available if the capability object
         'gamQosCapabilitiesHasDscp' is True."
    ::= { gamQosConfigGlobalsDscpEntry 3 }

gamQosConfigGlobalsDscpDpl OBJECT-TYPE
    SYNTAX      GAMUnsigned8
    MAX-ACCESS  read-write
    STATUS      current
    DESCRIPTION
        "The DPL (Drop Precedence Level) which the DSCP value maps to.
         
         Valid range is qosCapabilitiesDplMin-qosCapabilitiesDplMax.
         
         This object is only available if the capability object
         'gamQosCapabilitiesHasDscp' is True."
    ::= { gamQosConfigGlobalsDscpEntry 4 }

gamQosConfigGlobalsDscpIngressTranslation OBJECT-TYPE
    SYNTAX      Dscp
    MAX-ACCESS  read-write
    STATUS      current
    DESCRIPTION
        "The new classified DSCP value which the original DSCP value is replaced
         with if 'DscpTranslate' is enabled on the interface
         
         This object is only available if the capability object
         'gamQosCapabilitiesHasDscp' is True."
    ::= { gamQosConfigGlobalsDscpEntry 5 }

gamQosConfigGlobalsDscpClassify OBJECT-TYPE
    SYNTAX      TruthValue
    MAX-ACCESS  read-write
    STATUS      current
    DESCRIPTION
        "If true, then packets received on interfaces where 'DscpClassify' is
         set to 'selected' will be classified to a new DSCP value based on the
         values configured in the qosConfigGlobalsCosToDscpTable.
         
         This object is only available if the capability object
         'gamQosCapabilitiesHasDscp' is True."
    ::= { gamQosConfigGlobalsDscpEntry 6 }

gamQosConfigGlobalsDscpEgressTranslation OBJECT-TYPE
    SYNTAX      Dscp
    MAX-ACCESS  read-write
    STATUS      current
    DESCRIPTION
        "The new DSCP value that will be written into the packet at egress if
         'DscpRemark' on the interface is set to 'remap' or 'remapDp'.
         
         If 'remapDp' is set then only packets classified to Dpl 0 will use this
         table.
         
         This object is only available if the capability object
         'gamQosCapabilitiesHasDscp' is True."
    ::= { gamQosConfigGlobalsDscpEntry 7 }

gamQosConfigGlobalsDscpEgressTranslationDp1 OBJECT-TYPE
    SYNTAX      Dscp
    MAX-ACCESS  read-write
    STATUS      current
    DESCRIPTION
        "The new DSCP value that will be written into the packet at egress if
         'DscpRemark' on the interface is set to 'remapDp'.
         
         Only packets classified to Dpl 1 will use this table.
         
         
         
         This object is only available if the capability object
         'gamQosCapabilitiesHasDscpDplRemarking' is True."
    ::= { gamQosConfigGlobalsDscpEntry 8 }

gamQosConfigGlobalsCosToDscpTable OBJECT-TYPE
    SYNTAX      SEQUENCE OF GAMQosConfigGlobalsCosToDscpEntry
    MAX-ACCESS  not-accessible
    STATUS      current
    DESCRIPTION
        "This table has 8 entries, one for each Cos value.
         
         This is an optional table and is only present if qosCapabilitiesHasDscp
         is true."
    ::= { gamQosConfigGlobals 4 }

gamQosConfigGlobalsCosToDscpEntry OBJECT-TYPE
    SYNTAX      GAMQosConfigGlobalsCosToDscpEntry
    MAX-ACCESS  not-accessible
    STATUS      current
    DESCRIPTION
        "Each row contains the configuration for a specific Cos"
    INDEX       { gamQosConfigGlobalsCosToDscpCos }
    ::= { gamQosConfigGlobalsCosToDscpTable 1 }

GAMQosConfigGlobalsCosToDscpEntry ::= SEQUENCE {
    gamQosConfigGlobalsCosToDscpCos      Integer32,
    gamQosConfigGlobalsCosToDscpDscp     Dscp,
    gamQosConfigGlobalsCosToDscpDscpDp1  Dscp,
    gamQosConfigGlobalsCosToDscpDscpDp2  Dscp,
    gamQosConfigGlobalsCosToDscpDscpDp3  Dscp
}

gamQosConfigGlobalsCosToDscpCos OBJECT-TYPE
    SYNTAX      Integer32 (0..7)
    MAX-ACCESS  accessible-for-notify
    STATUS      current
    DESCRIPTION
        "CoS index.
         
         This object is only available if the capability object
         'gamQosCapabilitiesHasDscp' is True."
    ::= { gamQosConfigGlobalsCosToDscpEntry 1 }

gamQosConfigGlobalsCosToDscpDscp OBJECT-TYPE
    SYNTAX      Dscp
    MAX-ACCESS  read-write
    STATUS      current
    DESCRIPTION
        "If qosCapabilitiesHasDscpDplClassification is true: This is the DSCP
         value which the classified CoS value maps to when the classified DPL is
         0.
         
         If qosCapabilitiesHasDscpDplClassification is false: This is the DSCP
         value which the classified CoS value maps to.
         
         This object is only available if the capability object
         'gamQosCapabilitiesHasDscp' is True."
    ::= { gamQosConfigGlobalsCosToDscpEntry 2 }

gamQosConfigGlobalsCosToDscpDscpDp1 OBJECT-TYPE
    SYNTAX      Dscp
    MAX-ACCESS  read-write
    STATUS      current
    DESCRIPTION
        "The DSCP value which the classified CoS value maps to when the
         classified DPL is 1.
         
         
         
         This object is only available if the capability object
         'gamQosCapabilitiesHasDscpDplClassification' is True."
    ::= { gamQosConfigGlobalsCosToDscpEntry 3 }

gamQosConfigGlobalsCosToDscpDscpDp2 OBJECT-TYPE
    SYNTAX      Dscp
    MAX-ACCESS  read-write
    STATUS      current
    DESCRIPTION
        "The DSCP value which the classified CoS value maps to when the
         classified DPL is 2.
         
         
         
         This object is only available if the capability object
         'gamQosCapabilitiesHasDscpDp2' is True."
    ::= { gamQosConfigGlobalsCosToDscpEntry 4 }

gamQosConfigGlobalsCosToDscpDscpDp3 OBJECT-TYPE
    SYNTAX      Dscp
    MAX-ACCESS  read-write
    STATUS      current
    DESCRIPTION
        "The DSCP value which the classified CoS value maps to when the
         classified DPL is 3.
         
         
         
         This object is only available if the capability object
         'gamQosCapabilitiesHasDscpDp3' is True."
    ::= { gamQosConfigGlobalsCosToDscpEntry 5 }

gamQosConfigGlobalsPcpCosMapTable OBJECT-TYPE
    SYNTAX      SEQUENCE OF GAMQosConfigGlobalsPcpCosMapEntry
    MAX-ACCESS  not-accessible
    STATUS      current
    DESCRIPTION
        "This table contains the configuration of PCP to CoS mapping. The last
         entry (PCP 7)is read-only."
    ::= { gamQosConfigGlobals 5 }

gamQosConfigGlobalsPcpCosMapEntry OBJECT-TYPE
    SYNTAX      GAMQosConfigGlobalsPcpCosMapEntry
    MAX-ACCESS  not-accessible
    STATUS      current
    DESCRIPTION
        "Each row contains the CoS map for a single PCP. The last entry (PCP
         7)is read-only."
    INDEX       { gamQosConfigGlobalsPcpCosMapPcp }
    ::= { gamQosConfigGlobalsPcpCosMapTable 1 }

GAMQosConfigGlobalsPcpCosMapEntry ::= SEQUENCE {
    gamQosConfigGlobalsPcpCosMapPcp  Integer32,
    gamQosConfigGlobalsPcpCosMapCos  GAMUnsigned8
}

gamQosConfigGlobalsPcpCosMapPcp OBJECT-TYPE
    SYNTAX      Integer32 (0..7)
    MAX-ACCESS  accessible-for-notify
    STATUS      current
    DESCRIPTION
        "PCP index."
    ::= { gamQosConfigGlobalsPcpCosMapEntry 1 }

gamQosConfigGlobalsPcpCosMapCos OBJECT-TYPE
    SYNTAX      GAMUnsigned8
    MAX-ACCESS  read-write
    STATUS      current
    DESCRIPTION
        "The CoS value which this entry maps to.
         
         Valid range is qosCapabilitiesClassMin-qosCapabilitiesClassMax."
    ::= { gamQosConfigGlobalsPcpCosMapEntry 2 }

gamQosConfigInterface OBJECT IDENTIFIER
    ::= { gamQosConfig 2 }

gamQosConfigInterfaceTable OBJECT-TYPE
    SYNTAX      SEQUENCE OF GAMQosConfigInterfaceEntry
    MAX-ACCESS  not-accessible
    STATUS      current
    DESCRIPTION
        "This table provides QoS configuration for QoS manageable interfaces"
    ::= { gamQosConfigInterface 1 }

gamQosConfigInterfaceEntry OBJECT-TYPE
    SYNTAX      GAMQosConfigInterfaceEntry
    MAX-ACCESS  not-accessible
    STATUS      current
    DESCRIPTION
        "Each row contains the configuration for a specific interface"
    INDEX       { gamQosConfigInterfaceIfIndex }
    ::= { gamQosConfigInterfaceTable 1 }

GAMQosConfigInterfaceEntry ::= SEQUENCE {
    gamQosConfigInterfaceIfIndex           GAMInterfaceIndex,
    gamQosConfigInterfaceCos               Unsigned32,
    gamQosConfigInterfaceDpl               GAMUnsigned8,
    gamQosConfigInterfacePcp               Unsigned32,
    gamQosConfigInterfaceDei               GAMUnsigned8,
    gamQosConfigInterfaceTrustTag          TruthValue,
    gamQosConfigInterfaceTrustDscp         TruthValue,
    gamQosConfigInterfaceDwrrCount         GAMUnsigned8,
    gamQosConfigInterfaceTagRemarkingMode  GAMQosTagRemarkingMode,
    gamQosConfigInterfaceTagPcp            Unsigned32,
    gamQosConfigInterfaceTagDei            GAMUnsigned8,
    gamQosConfigInterfaceDscpTranslate     TruthValue,
    gamQosConfigInterfaceDscpClassify      GAMQosDscpClassify,
    gamQosConfigInterfaceDscpRemark        GAMQosDscpRemark,
    gamQosConfigInterfaceQceAddressMode    TruthValue,
    gamQosConfigInterfaceQceKeyType        GAMVcapKeyType,
    gamQosConfigInterfaceWredGroup         Unsigned32,
    gamQosConfigInterfaceIngressMap        GAMUnsigned16,
    gamQosConfigInterfaceEgressMap         GAMUnsigned16,
    gamQosConfigInterfaceCosId             GAMUnsigned8
}

gamQosConfigInterfaceIfIndex OBJECT-TYPE
    SYNTAX      GAMInterfaceIndex
    MAX-ACCESS  accessible-for-notify
    STATUS      current
    DESCRIPTION
        "Logical interface index."
    ::= { gamQosConfigInterfaceEntry 1 }

gamQosConfigInterfaceCos OBJECT-TYPE
    SYNTAX      Unsigned32
    MAX-ACCESS  read-write
    STATUS      current
    DESCRIPTION
        "The default CoS value a packet is classified to.
         
         Valid range is qosCapabilitiesClassMin-qosCapabilitiesClassMax."
    ::= { gamQosConfigInterfaceEntry 2 }

gamQosConfigInterfaceDpl OBJECT-TYPE
    SYNTAX      GAMUnsigned8
    MAX-ACCESS  read-write
    STATUS      current
    DESCRIPTION
        "The default DPL (Drop Precedence Level) a packet is classified to.
         
         Valid range is qosCapabilitiesDplMin-qosCapabilitiesDplMax."
    ::= { gamQosConfigInterfaceEntry 3 }

gamQosConfigInterfacePcp OBJECT-TYPE
    SYNTAX      Unsigned32
    MAX-ACCESS  read-write
    STATUS      current
    DESCRIPTION
        "The default PCP value a packet is classified to.
         
         Valid range is 0-7.
         
         
         
         This object is only available if the capability object
         'gamQosCapabilitiesHasDefaultPcpAndDei' is True."
    ::= { gamQosConfigInterfaceEntry 4 }

gamQosConfigInterfaceDei OBJECT-TYPE
    SYNTAX      GAMUnsigned8
    MAX-ACCESS  read-write
    STATUS      current
    DESCRIPTION
        "The default DEI value a packet is classified to.
         
         Valid range is 0-1.
         
         
         
         This object is only available if the capability object
         'gamQosCapabilitiesHasDefaultPcpAndDei' is True."
    ::= { gamQosConfigInterfaceEntry 5 }

gamQosConfigInterfaceTrustTag OBJECT-TYPE
    SYNTAX      TruthValue
    MAX-ACCESS  read-write
    STATUS      current
    DESCRIPTION
        "If true and the packet is VLAN tagged, then the CoS and DPL assigned to
         the packet is the PCP and DEI value in the packet mapped to a CoS and
         DPL value defined in the qosConfigInterfaceTagToCosTable.
         
         
         
         This object is only available if the capability object
         'gamQosCapabilitiesHasTrustTag' is True."
    ::= { gamQosConfigInterfaceEntry 6 }

gamQosConfigInterfaceTrustDscp OBJECT-TYPE
    SYNTAX      TruthValue
    MAX-ACCESS  read-write
    STATUS      current
    DESCRIPTION
        "If true and the packet type is IPv4 or IPv6 and the packet DSCP value
         is trusted in qosConfigGlobalsDscpTable, then the CoS and DPL assigned
         to the packet is the DSCP value in the packet mapped to a CoS and DPL
         value defined in the qosConfigGlobalsDscpTable.
         
         
         
         This object is only available if the capability object
         'gamQosCapabilitiesHasDscp' is True."
    ::= { gamQosConfigInterfaceEntry 7 }

gamQosConfigInterfaceDwrrCount OBJECT-TYPE
    SYNTAX      GAMUnsigned8
    MAX-ACCESS  read-write
    STATUS      current
    DESCRIPTION
        "The number of queues that are running Deficit Weighted Round Robin
         scheduling.
         
         This value is restricted to 0 or one of the values defined by
         qosCapabilitiesDwrrCountMask."
    ::= { gamQosConfigInterfaceEntry 8 }

gamQosConfigInterfaceTagRemarkingMode OBJECT-TYPE
    SYNTAX      GAMQosTagRemarkingMode
    MAX-ACCESS  read-write
    STATUS      current
    DESCRIPTION
        "Selects the tag remarking mode for egress. Valid values are:
         
         'classified' : Remark the tag with the classified values of PCP and
         DEI.
         
         'default' : Remark the tag with the configured TagPcp and TagDei.
         
         'mapped' : Remark the tag with the values from the classified CoS and
         DPL mapped through the qosConfigInterfaceCosToTagTable.
         
         
         
         This object is only available if the capability object
         'gamQosCapabilitiesHasTagRemarking' is True."
    ::= { gamQosConfigInterfaceEntry 9 }

gamQosConfigInterfaceTagPcp OBJECT-TYPE
    SYNTAX      Unsigned32
    MAX-ACCESS  read-write
    STATUS      current
    DESCRIPTION
        "The PCP value to put in the packet if TagRemarkingMode is set to
         'default'.
         
         Valid range is 0-7.
         
         
         
         This object is only available if the capability object
         'gamQosCapabilitiesHasTagRemarking' is True."
    ::= { gamQosConfigInterfaceEntry 10 }

gamQosConfigInterfaceTagDei OBJECT-TYPE
    SYNTAX      GAMUnsigned8
    MAX-ACCESS  read-write
    STATUS      current
    DESCRIPTION
        "The DEI value to put in the packet if TagRemarkingMode is set to
         'default'.
         
         Valid range is 0-1.
         
         
         
         This object is only available if the capability object
         'gamQosCapabilitiesHasTagRemarking' is True."
    ::= { gamQosConfigInterfaceEntry 11 }

gamQosConfigInterfaceDscpTranslate OBJECT-TYPE
    SYNTAX      TruthValue
    MAX-ACCESS  read-write
    STATUS      current
    DESCRIPTION
        "If true then the classified DSCP value is the DSCP value in the packed
         mapped to a new DSCP value defined in
         qosConfigGlobalsDscpTable.IngressTranslation.
         
         
         
         This object is only available if the capability object
         'gamQosCapabilitiesHasDscp' is True."
    ::= { gamQosConfigInterfaceEntry 12 }

gamQosConfigInterfaceDscpClassify OBJECT-TYPE
    SYNTAX      GAMQosDscpClassify
    MAX-ACCESS  read-write
    STATUS      current
    DESCRIPTION
        "If qosCapabilitiesHasDscpDplClassification is true: Selects if and how
         the classified DSCP is based on the classified CoS and DPL for IPv4 and
         IPv6 packets on ingress.
         
         If a packet is selected for being classified to a new DSCP, the
         classification in based on the classified CoS mapped to a new DSCP
         value through the qosConfigGlobalsCosToDscpTable. If the classified DPL
         is 1, the new DSCP value is taken from the DscpDp1 entry, otherwise it
         is taken from the Dscp entry. Valid values are:
         
         'none' : Always classify to the DSCP value in the received packet and
         ignore the classified CoS and DPL.
         
         'zero' : If the DSCP value in the received packet is 0, then classify
         to a new DSCP value based on the classified CoS and DPL.
         
         'selected' : If the DSCP value in the received packet is enabled in
         qosConfigGlobalsDscpTable.Classify, then classify to a new DSCP value
         based on the classified CoS and DPL.
         
         'all' : Always classify to a new DSCP value based on the classified CoS
         and DPL.
         
         
         
         If qosCapabilitiesHasDscpDplClassification is false: Selects if and how
         the classified DSCP is based on the classified CoS for IPv4 and IPv6
         packets on ingress.
         
         If a packet is selected for being classified to a new DSCP, the
         classification in based on the classified CoS mapped to a new DSCP
         value through the qosConfigGlobalsCosToDscpTable.Dscp Valid values are:
         
         'none' : Always classify to the DSCP value in the received packet and
         ignore the classified CoS.
         
         'zero' : If the DSCP value in the received packet is 0, then classify
         to a new DSCP value based on the classified CoS.
         
         'selected' : If the DSCP value in the received packet is enabled in
         qosConfigGlobalsDscpTable.Classify, then classify to a new DSCP value
         based on the classified CoS.
         
         'all' : Always classify to a new DSCP value based on the classified
         CoS.
         
         
         
         This object is only available if the capability object
         'gamQosCapabilitiesHasDscp' is True."
    ::= { gamQosConfigInterfaceEntry 13 }

gamQosConfigInterfaceDscpRemark OBJECT-TYPE
    SYNTAX      GAMQosDscpRemark
    MAX-ACCESS  read-write
    STATUS      current
    DESCRIPTION
        "If qosCapabilitiesHasDscpDplRemarking is true: Selects if and how the
         classified DSCP is written into the packet at egress. Valid values are:
         
         'disabled' : Do not write the classified DSCP into the packet.
         
         'rewrite' : Write the classified DSCP into the packet.
         
         'remap' : Remap the classified DSCP through qosConfigGlobalsDscpTable,
         and write the value from EgressTranslation into the packet.
         
         'remapDp' : Remap the classified DSCP through
         qosConfigGlobalsDscpTable. If the classified DPL is 0 then write the
         value from EgressTranslation into the packet, otherwise write the value
         from EgressTranslationDp1 into the packet.
         
         If qosCapabilitiesHasDscpDplRemarking is false: Selects if and how the
         classified DSCP is written into the packet at egress. Valid values are:
         
         'disabled' : Do not write the classified DSCP into the packet.
         
         'rewrite' : Write the classified DSCP into the packet.
         
         'remap' : Remap the classified DSCP through qosConfigGlobalsDscpTable,
         and write the value from EgressTranslation into the packet.
         
         
         
         This object is only available if the capability object
         'gamQosCapabilitiesHasDscp' is True."
    ::= { gamQosConfigInterfaceEntry 14 }

gamQosConfigInterfaceQceAddressMode OBJECT-TYPE
    SYNTAX      TruthValue
    MAX-ACCESS  read-write
    STATUS      current
    DESCRIPTION
        "If false, the QCE classification for this interface is based on source
         (SMAC/SIP) addresses.
         
         If true, the QCE classification for this interface is based on
         destination (DMAC/DIP) addresses.
         
         This parameter is only used when qosCapabilitiesHasQceKeyType is false
         or QceKeyType is normal.
         
         
         
         This object is only available if the capability object
         'gamQosCapabilitiesHasQceAddressMode' is True."
    ::= { gamQosConfigInterfaceEntry 15 }

gamQosConfigInterfaceQceKeyType OBJECT-TYPE
    SYNTAX      GAMVcapKeyType
    MAX-ACCESS  read-write
    STATUS      current
    DESCRIPTION
        "The key type specifying the key generated for packets received on the
         interface. Valid values are:
         
         'normal' : Half key, match outer tag, SIP and SMAC.
         
         'doubleTag' : Quarter key, match inner and outer tag.
         
         'ipAddr' : Half key, match inner and outer tag, SIP and DIP. For non-IP
         frames, match outer tag only.
         
         'macIpAddr' : Full key, match inner and outer tag, SMAC, DMAC, SIP and
         DIP.
         
         Filtering on DMAC type (unicast/multicast/broadcast) is supported for
         any key type.
         
         
         
         This object is only available if the capability object
         'gamQosCapabilitiesHasQceKeyType' is True."
    ::= { gamQosConfigInterfaceEntry 16 }

gamQosConfigInterfaceWredGroup OBJECT-TYPE
    SYNTAX      Unsigned32
    MAX-ACCESS  read-write
    STATUS      current
    DESCRIPTION
        "The WRED group an interface is a member of.
         
         
         
         This object is only available if the capability object
         'gamQosCapabilitiesHasWredV3' is True."
    ::= { gamQosConfigInterfaceEntry 17 }

gamQosConfigInterfaceIngressMap OBJECT-TYPE
    SYNTAX      GAMUnsigned16
    MAX-ACCESS  read-write
    STATUS      current
    DESCRIPTION
        "The Ingress Map an interface is associated with for packet
         classification.
         
         Valid range is
         qosCapabilitiesIngressMapIdMin-qosCapabilitiesIngressMapIdMax and 4095
         for NONE
         
         This object is only available if the capability object
         'gamQosCapabilitiesHasIngressMap' is True."
    ::= { gamQosConfigInterfaceEntry 18 }

gamQosConfigInterfaceEgressMap OBJECT-TYPE
    SYNTAX      GAMUnsigned16
    MAX-ACCESS  read-write
    STATUS      current
    DESCRIPTION
        "The Egress Map an interface is associated with for packet mapping.
         
         Valid range is
         qosCapabilitiesEgressMapIdMin-qosCapabilitiesEgressMapIdMax and 4095
         for NONE
         
         This object is only available if the capability object
         'gamQosCapabilitiesHasEgressMap' is True."
    ::= { gamQosConfigInterfaceEntry 19 }

gamQosConfigInterfaceCosId OBJECT-TYPE
    SYNTAX      GAMUnsigned8
    MAX-ACCESS  read-write
    STATUS      current
    DESCRIPTION
        "The default COSID value a packet is classified to.
         
         Valid range is qosCapabilitiesCosIdMin-qosCapabilitiesCosIdMax.
         
         This object is only available if the capability object
         'gamQosCapabilitiesHasCosIdClassification' is True."
    ::= { gamQosConfigInterfaceEntry 20 }

gamQosConfigInterfaceTagToCosTable OBJECT-TYPE
    SYNTAX      SEQUENCE OF GAMQosConfigInterfaceTagToCosEntry
    MAX-ACCESS  not-accessible
    STATUS      current
    DESCRIPTION
        "This table contains the mapping of (interface, PCP, DEI) to (CoS, DPL)
         values.
         
         The mappings given by this table is used for all tagged packets
         received on an interface if and only if that interface has the value of
         TrustTag set to 'true'
         
         This is an optional table and is only present if
         qosCapabilitiesHasFixedTagCosMap is false and
         qosCapabilitiesHasTagClassification is true."
    ::= { gamQosConfigInterface 2 }

gamQosConfigInterfaceTagToCosEntry OBJECT-TYPE
    SYNTAX      GAMQosConfigInterfaceTagToCosEntry
    MAX-ACCESS  not-accessible
    STATUS      current
    DESCRIPTION
        "Each row contains the mapping from (interface, PCP, DEI) to (CoS, DPL)
         values."
    INDEX       { gamQosConfigInterfaceTagToCosIfIndex,
                  gamQosConfigInterfaceTagToCosPcp,
                  gamQosConfigInterfaceTagToCosDei }
    ::= { gamQosConfigInterfaceTagToCosTable 1 }

GAMQosConfigInterfaceTagToCosEntry ::= SEQUENCE {
    gamQosConfigInterfaceTagToCosIfIndex  GAMInterfaceIndex,
    gamQosConfigInterfaceTagToCosPcp      Integer32,
    gamQosConfigInterfaceTagToCosDei      Integer32,
    gamQosConfigInterfaceTagToCosCos      Unsigned32,
    gamQosConfigInterfaceTagToCosDpl      GAMUnsigned8
}

gamQosConfigInterfaceTagToCosIfIndex OBJECT-TYPE
    SYNTAX      GAMInterfaceIndex
    MAX-ACCESS  accessible-for-notify
    STATUS      current
    DESCRIPTION
        "Logical interface index.
         
         This object is only available if the capability object
         'gamQosCapabilitiesHasTrustTag' is True."
    ::= { gamQosConfigInterfaceTagToCosEntry 1 }

gamQosConfigInterfaceTagToCosPcp OBJECT-TYPE
    SYNTAX      Integer32 (0..7)
    MAX-ACCESS  accessible-for-notify
    STATUS      current
    DESCRIPTION
        "PCP index.
         
         This object is only available if the capability object
         'gamQosCapabilitiesHasTrustTag' is True."
    ::= { gamQosConfigInterfaceTagToCosEntry 2 }

gamQosConfigInterfaceTagToCosDei OBJECT-TYPE
    SYNTAX      Integer32 (0..1)
    MAX-ACCESS  accessible-for-notify
    STATUS      current
    DESCRIPTION
        "DEI index.
         
         This object is only available if the capability object
         'gamQosCapabilitiesHasTrustTag' is True."
    ::= { gamQosConfigInterfaceTagToCosEntry 3 }

gamQosConfigInterfaceTagToCosCos OBJECT-TYPE
    SYNTAX      Unsigned32
    MAX-ACCESS  read-write
    STATUS      current
    DESCRIPTION
        "The CoS value which this entry maps to.
         
         Valid range is qosCapabilitiesClassMin-qosCapabilitiesClassMax.
         
         This object is only available if the capability object
         'gamQosCapabilitiesHasTrustTag' is True."
    ::= { gamQosConfigInterfaceTagToCosEntry 4 }

gamQosConfigInterfaceTagToCosDpl OBJECT-TYPE
    SYNTAX      GAMUnsigned8
    MAX-ACCESS  read-write
    STATUS      current
    DESCRIPTION
        "The DPL (Drop Precedence Level) value which this entry maps to.
         
         Valid range is qosCapabilitiesDplMin-qosCapabilitiesDplMax.
         
         This object is only available if the capability object
         'gamQosCapabilitiesHasTrustTag' is True."
    ::= { gamQosConfigInterfaceTagToCosEntry 5 }

gamQosConfigInterfaceCosToTagTable OBJECT-TYPE
    SYNTAX      SEQUENCE OF GAMQosConfigInterfaceCosToTagEntry
    MAX-ACCESS  not-accessible
    STATUS      current
    DESCRIPTION
        "This table contains the mapping of (interface, CoS, DPL) to (PCP, DEI)
         values.
         
         The mappings given by this table is used for packets transmitted on an
         interface if and only if that interface has the value of
         TagRemarkingMode set to 'mapped'
         
         This is an optional table and is only present if
         qosCapabilitiesHasTagRemarking is true."
    ::= { gamQosConfigInterface 3 }

gamQosConfigInterfaceCosToTagEntry OBJECT-TYPE
    SYNTAX      GAMQosConfigInterfaceCosToTagEntry
    MAX-ACCESS  not-accessible
    STATUS      current
    DESCRIPTION
        "Each row contains the mapping from (interface, CoS, DPL) to (PCP, DEI)
         values."
    INDEX       { gamQosConfigInterfaceCosToTagIfIndex,
                  gamQosConfigInterfaceCosToTagCos,
                  gamQosConfigInterfaceCosToTagDpl }
    ::= { gamQosConfigInterfaceCosToTagTable 1 }

GAMQosConfigInterfaceCosToTagEntry ::= SEQUENCE {
    gamQosConfigInterfaceCosToTagIfIndex  GAMInterfaceIndex,
    gamQosConfigInterfaceCosToTagCos      Integer32,
    gamQosConfigInterfaceCosToTagDpl      Integer32,
    gamQosConfigInterfaceCosToTagPcp      Unsigned32,
    gamQosConfigInterfaceCosToTagDei      GAMUnsigned8
}

gamQosConfigInterfaceCosToTagIfIndex OBJECT-TYPE
    SYNTAX      GAMInterfaceIndex
    MAX-ACCESS  accessible-for-notify
    STATUS      current
    DESCRIPTION
        "Logical interface index.
         
         This object is only available if the capability object
         'gamQosCapabilitiesHasTagRemarking' is True."
    ::= { gamQosConfigInterfaceCosToTagEntry 1 }

gamQosConfigInterfaceCosToTagCos OBJECT-TYPE
    SYNTAX      Integer32 (0..7)
    MAX-ACCESS  accessible-for-notify
    STATUS      current
    DESCRIPTION
        "CoS index.
         
         This object is only available if the capability object
         'gamQosCapabilitiesHasTagRemarking' is True."
    ::= { gamQosConfigInterfaceCosToTagEntry 2 }

gamQosConfigInterfaceCosToTagDpl OBJECT-TYPE
    SYNTAX      Integer32 (0..1)
    MAX-ACCESS  accessible-for-notify
    STATUS      current
    DESCRIPTION
        "Color index. It is 0 for DPL 0 and 1 for all other values of DPL
         
         This object is only available if the capability object
         'gamQosCapabilitiesHasTagRemarking' is True."
    ::= { gamQosConfigInterfaceCosToTagEntry 3 }

gamQosConfigInterfaceCosToTagPcp OBJECT-TYPE
    SYNTAX      Unsigned32
    MAX-ACCESS  read-write
    STATUS      current
    DESCRIPTION
        "The PCP value which this entry maps to.
         
         Valid range is 0-7.
         
         This object is only available if the capability object
         'gamQosCapabilitiesHasTagRemarking' is True."
    ::= { gamQosConfigInterfaceCosToTagEntry 4 }

gamQosConfigInterfaceCosToTagDei OBJECT-TYPE
    SYNTAX      GAMUnsigned8
    MAX-ACCESS  read-write
    STATUS      current
    DESCRIPTION
        "The DEI value which this entry maps to.
         
         Valid range is 0-1.
         
         This object is only available if the capability object
         'gamQosCapabilitiesHasTagRemarking' is True."
    ::= { gamQosConfigInterfaceCosToTagEntry 5 }

gamQosConfigInterfacePolicerTable OBJECT-TYPE
    SYNTAX      SEQUENCE OF GAMQosConfigInterfacePolicerEntry
    MAX-ACCESS  not-accessible
    STATUS      current
    DESCRIPTION
        "This table provides policer configuration for an interface"
    ::= { gamQosConfigInterface 4 }

gamQosConfigInterfacePolicerEntry OBJECT-TYPE
    SYNTAX      GAMQosConfigInterfacePolicerEntry
    MAX-ACCESS  not-accessible
    STATUS      current
    DESCRIPTION
        "Each row contains the configuration for a specific policer"
    INDEX       { gamQosConfigInterfacePolicerIfIndex }
    ::= { gamQosConfigInterfacePolicerTable 1 }

GAMQosConfigInterfacePolicerEntry ::= SEQUENCE {
    gamQosConfigInterfacePolicerIfIndex      GAMInterfaceIndex,
    gamQosConfigInterfacePolicerEnable       TruthValue,
    gamQosConfigInterfacePolicerFrameRate    TruthValue,
    gamQosConfigInterfacePolicerFlowControl  TruthValue,
    gamQosConfigInterfacePolicerCir          Unsigned32
}

gamQosConfigInterfacePolicerIfIndex OBJECT-TYPE
    SYNTAX      GAMInterfaceIndex
    MAX-ACCESS  accessible-for-notify
    STATUS      current
    DESCRIPTION
        "Logical interface index."
    ::= { gamQosConfigInterfacePolicerEntry 1 }

gamQosConfigInterfacePolicerEnable OBJECT-TYPE
    SYNTAX      TruthValue
    MAX-ACCESS  read-write
    STATUS      current
    DESCRIPTION
        "If true, the port policer is enabled."
    ::= { gamQosConfigInterfacePolicerEntry 2 }

gamQosConfigInterfacePolicerFrameRate OBJECT-TYPE
    SYNTAX      TruthValue
    MAX-ACCESS  read-write
    STATUS      current
    DESCRIPTION
        "If true, the rate is measured in fps instead of kbps."
    ::= { gamQosConfigInterfacePolicerEntry 3 }

gamQosConfigInterfacePolicerFlowControl OBJECT-TYPE
    SYNTAX      TruthValue
    MAX-ACCESS  read-write
    STATUS      current
    DESCRIPTION
        "If true, and flow control is enabled on the interface, then issue flow
         control pause frames instead of discarding frames.
         
         
         
         This object is only available if the capability object
         'gamQosCapabilitiesHasPortPolicersFc' is True."
    ::= { gamQosConfigInterfacePolicerEntry 4 }

gamQosConfigInterfacePolicerCir OBJECT-TYPE
    SYNTAX      Unsigned32
    MAX-ACCESS  read-write
    STATUS      current
    DESCRIPTION
        "Committed Information Rate. Measured in kbps if FrameRate is false and
         fps if FrameRate is true.
         
         Valid range is from the smallest value of
         qosCapabilitiesPortPolicerBitRateMin and
         qosCapabilitiesPortPolicerFrameRateMin to the largest value of
         qosCapabilitiesPortPolicerBitRateMax and
         qosCapabilitiesPortPolicerFrameRateMax.
         
         "
    ::= { gamQosConfigInterfacePolicerEntry 5 }

gamQosConfigInterfaceQueuePolicerTable OBJECT-TYPE
    SYNTAX      SEQUENCE OF GAMQosConfigInterfaceQueuePolicerEntry
    MAX-ACCESS  not-accessible
    STATUS      current
    DESCRIPTION
        "This table provides queue policer configuration for interfaces
         
         This is an optional table and is only present if
         qosCapabilitiesHasPortQueuePolicers is true."
    ::= { gamQosConfigInterface 5 }

gamQosConfigInterfaceQueuePolicerEntry OBJECT-TYPE
    SYNTAX      GAMQosConfigInterfaceQueuePolicerEntry
    MAX-ACCESS  not-accessible
    STATUS      current
    DESCRIPTION
        "Each row contains the configuration for a specific queue policer"
    INDEX       { gamQosConfigInterfaceQueuePolicerIfIndex,
                  gamQosConfigInterfaceQueuePolicerQueue }
    ::= { gamQosConfigInterfaceQueuePolicerTable 1 }

GAMQosConfigInterfaceQueuePolicerEntry ::= SEQUENCE {
    gamQosConfigInterfaceQueuePolicerIfIndex  GAMInterfaceIndex,
    gamQosConfigInterfaceQueuePolicerQueue    Integer32,
    gamQosConfigInterfaceQueuePolicerEnable   TruthValue,
    gamQosConfigInterfaceQueuePolicerCir      Unsigned32
}

gamQosConfigInterfaceQueuePolicerIfIndex OBJECT-TYPE
    SYNTAX      GAMInterfaceIndex
    MAX-ACCESS  accessible-for-notify
    STATUS      current
    DESCRIPTION
        "Logical interface index.
         
         This object is only available if the capability object
         'gamQosCapabilitiesHasPortQueuePolicers' is True."
    ::= { gamQosConfigInterfaceQueuePolicerEntry 1 }

gamQosConfigInterfaceQueuePolicerQueue OBJECT-TYPE
    SYNTAX      Integer32 (0..7)
    MAX-ACCESS  accessible-for-notify
    STATUS      current
    DESCRIPTION
        "Queue index.
         
         This object is only available if the capability object
         'gamQosCapabilitiesHasPortQueuePolicers' is True."
    ::= { gamQosConfigInterfaceQueuePolicerEntry 2 }

gamQosConfigInterfaceQueuePolicerEnable OBJECT-TYPE
    SYNTAX      TruthValue
    MAX-ACCESS  read-write
    STATUS      current
    DESCRIPTION
        "If true, the queue policer is enabled.
         
         This object is only available if the capability object
         'gamQosCapabilitiesHasPortQueuePolicers' is True."
    ::= { gamQosConfigInterfaceQueuePolicerEntry 3 }

gamQosConfigInterfaceQueuePolicerCir OBJECT-TYPE
    SYNTAX      Unsigned32
    MAX-ACCESS  read-write
    STATUS      current
    DESCRIPTION
        "Committed Information Rate. Measured in kbps.
         
         Valid range is from the smallest value of
         qosCapabilitiesQueuePolicerBitRateMin and
         qosCapabilitiesQueuePolicerFrameRateMin to the largest value of
         qosCapabilitiesQueuePolicerBitRateMax and
         qosCapabilitiesQueuePolicerFrameRateMax.
         
         
         
         This object is only available if the capability object
         'gamQosCapabilitiesHasPortQueuePolicers' is True."
    ::= { gamQosConfigInterfaceQueuePolicerEntry 6 }

gamQosConfigInterfaceShaperTable OBJECT-TYPE
    SYNTAX      SEQUENCE OF GAMQosConfigInterfaceShaperEntry
    MAX-ACCESS  not-accessible
    STATUS      current
    DESCRIPTION
        "This table provides shaper configuration for an interface"
    ::= { gamQosConfigInterface 6 }

gamQosConfigInterfaceShaperEntry OBJECT-TYPE
    SYNTAX      GAMQosConfigInterfaceShaperEntry
    MAX-ACCESS  not-accessible
    STATUS      current
    DESCRIPTION
        "Each row contains the configuration for a specific shaper"
    INDEX       { gamQosConfigInterfaceShaperIfIndex }
    ::= { gamQosConfigInterfaceShaperTable 1 }

GAMQosConfigInterfaceShaperEntry ::= SEQUENCE {
    gamQosConfigInterfaceShaperIfIndex   GAMInterfaceIndex,
    gamQosConfigInterfaceShaperEnable    TruthValue,
    gamQosConfigInterfaceShaperCir       Unsigned32,
    gamQosConfigInterfaceShaperRateType  GAMQosShaperRateType
}

gamQosConfigInterfaceShaperIfIndex OBJECT-TYPE
    SYNTAX      GAMInterfaceIndex
    MAX-ACCESS  accessible-for-notify
    STATUS      current
    DESCRIPTION
        "Logical interface index."
    ::= { gamQosConfigInterfaceShaperEntry 1 }

gamQosConfigInterfaceShaperEnable OBJECT-TYPE
    SYNTAX      TruthValue
    MAX-ACCESS  read-write
    STATUS      current
    DESCRIPTION
        "If true, the port shaper is enabled."
    ::= { gamQosConfigInterfaceShaperEntry 2 }

gamQosConfigInterfaceShaperCir OBJECT-TYPE
    SYNTAX      Unsigned32
    MAX-ACCESS  read-write
    STATUS      current
    DESCRIPTION
        "Committed Information Rate. Measured in kbps.
         
         Valid range is from the smallest value of
         qosCapabilitiesPortShaperBitRateMin and
         qosCapabilitiesPortShaperFrameRateMin to the largest value of
         qosCapabilitiesPortShaperBitRateMax and
         qosCapabilitiesPortShaperFrameRateMax.
         
         "
    ::= { gamQosConfigInterfaceShaperEntry 3 }

gamQosConfigInterfaceShaperRateType OBJECT-TYPE
    SYNTAX      GAMQosShaperRateType
    MAX-ACCESS  read-write
    STATUS      current
    DESCRIPTION
        "Indicates the shaper's rate type.
         
         Valid selections are line (0) and data (1).
         
         
         
         This object is only available if the capability object
         'gamQosCapabilitiesHasShapersRt' is True."
    ::= { gamQosConfigInterfaceShaperEntry 4 }

gamQosConfigInterfaceQueueShaperTable OBJECT-TYPE
    SYNTAX      SEQUENCE OF GAMQosConfigInterfaceQueueShaperEntry
    MAX-ACCESS  not-accessible
    STATUS      current
    DESCRIPTION
        "This table provides queue shaper configuration for interfaces"
    ::= { gamQosConfigInterface 7 }

gamQosConfigInterfaceQueueShaperEntry OBJECT-TYPE
    SYNTAX      GAMQosConfigInterfaceQueueShaperEntry
    MAX-ACCESS  not-accessible
    STATUS      current
    DESCRIPTION
        "Each row contains the configuration for a specific queue shaper"
    INDEX       { gamQosConfigInterfaceQueueShaperIfIndex,
                  gamQosConfigInterfaceQueueShaperQueue }
    ::= { gamQosConfigInterfaceQueueShaperTable 1 }

GAMQosConfigInterfaceQueueShaperEntry ::= SEQUENCE {
    gamQosConfigInterfaceQueueShaperIfIndex   GAMInterfaceIndex,
    gamQosConfigInterfaceQueueShaperQueue     Integer32,
    gamQosConfigInterfaceQueueShaperEnable    TruthValue,
    gamQosConfigInterfaceQueueShaperExcess    TruthValue,
    gamQosConfigInterfaceQueueShaperCir       Unsigned32,
    gamQosConfigInterfaceQueueShaperRateType  GAMQosShaperRateType,
    gamQosConfigInterfaceQueueShaperCredit    TruthValue
}

gamQosConfigInterfaceQueueShaperIfIndex OBJECT-TYPE
    SYNTAX      GAMInterfaceIndex
    MAX-ACCESS  accessible-for-notify
    STATUS      current
    DESCRIPTION
        "Logical interface index."
    ::= { gamQosConfigInterfaceQueueShaperEntry 1 }

gamQosConfigInterfaceQueueShaperQueue OBJECT-TYPE
    SYNTAX      Integer32 (0..7)
    MAX-ACCESS  accessible-for-notify
    STATUS      current
    DESCRIPTION
        "Queue index."
    ::= { gamQosConfigInterfaceQueueShaperEntry 2 }

gamQosConfigInterfaceQueueShaperEnable OBJECT-TYPE
    SYNTAX      TruthValue
    MAX-ACCESS  read-write
    STATUS      current
    DESCRIPTION
        "If true, the queue shaper is enabled."
    ::= { gamQosConfigInterfaceQueueShaperEntry 3 }

gamQosConfigInterfaceQueueShaperExcess OBJECT-TYPE
    SYNTAX      TruthValue
    MAX-ACCESS  read-write
    STATUS      current
    DESCRIPTION
        "If true, then allow this queue to get a share of the excess bandwidth.
         
         Excess bandwidth is allowed if this shaper is closed and no other
         queues with open shapers have frames for transmission.
         
         
         
         This object is only available if the capability object
         'gamQosCapabilitiesHasQueueShapersExcess' is True."
    ::= { gamQosConfigInterfaceQueueShaperEntry 4 }

gamQosConfigInterfaceQueueShaperCir OBJECT-TYPE
    SYNTAX      Unsigned32
    MAX-ACCESS  read-write
    STATUS      current
    DESCRIPTION
        "Committed Information Rate. Measured in kbps.
         
         Valid range is from the smallest value of
         qosCapabilitiesQueueShaperBitRateMin and
         qosCapabilitiesQueueShaperFrameRateMin to the largest value of
         qosCapabilitiesQueueShaperBitRateMax and
         qosCapabilitiesQueueShaperFrameRateMax.
         
         "
    ::= { gamQosConfigInterfaceQueueShaperEntry 5 }

gamQosConfigInterfaceQueueShaperRateType OBJECT-TYPE
    SYNTAX      GAMQosShaperRateType
    MAX-ACCESS  read-write
    STATUS      current
    DESCRIPTION
        "Indicates the shaper's rate type.
         
         Valid selections are line (0) and data (1).
         
         NOTE: This configuration is valid only for Normal port mode. If the
         port is in Basic or Hierarchical mode, the rate-type will be stored and
         become active when the port is switched back to Normal Scheduling mode.
         
         
         
         This object is only available if the capability object
         'gamQosCapabilitiesHasShapersRt' is True."
    ::= { gamQosConfigInterfaceQueueShaperEntry 6 }

gamQosConfigInterfaceQueueShaperCredit OBJECT-TYPE
    SYNTAX      TruthValue
    MAX-ACCESS  read-write
    STATUS      current
    DESCRIPTION
        "If true, then this queue supports the credit based shaper.
         
         Creating burst capacity only when data is available.
         
         
         
         This object is only available if the capability object
         'gamQosCapabilitiesHasQueueShapersCredit' is True."
    ::= { gamQosConfigInterfaceQueueShaperEntry 7 }

gamQosConfigInterfaceSchedulerTable OBJECT-TYPE
    SYNTAX      SEQUENCE OF GAMQosConfigInterfaceSchedulerEntry
    MAX-ACCESS  not-accessible
    STATUS      current
    DESCRIPTION
        "This table contains the mapping of (interface, queue) to weight values.
         
         The mappings given by this table is used when an interface has the
         value of DwrrCount greater than 0.
         
         Read the qosSchedulerStatusTable in order to get the 'real' weights in
         percent as used by the hardware."
    ::= { gamQosConfigInterface 8 }

gamQosConfigInterfaceSchedulerEntry OBJECT-TYPE
    SYNTAX      GAMQosConfigInterfaceSchedulerEntry
    MAX-ACCESS  not-accessible
    STATUS      current
    DESCRIPTION
        "Each row contains the scheduler configuration for a specific queue."
    INDEX       { gamQosConfigInterfaceSchedulerIfIndex,
                  gamQosConfigInterfaceSchedulerQueue }
    ::= { gamQosConfigInterfaceSchedulerTable 1 }

GAMQosConfigInterfaceSchedulerEntry ::= SEQUENCE {
    gamQosConfigInterfaceSchedulerIfIndex          GAMInterfaceIndex,
    gamQosConfigInterfaceSchedulerQueue            Integer32,
    gamQosConfigInterfaceSchedulerWeight           GAMPercent,
    gamQosConfigInterfaceSchedulerCutThrough       TruthValue,
    gamQosConfigInterfaceSchedulerFramePreemption  TruthValue
}

gamQosConfigInterfaceSchedulerIfIndex OBJECT-TYPE
    SYNTAX      GAMInterfaceIndex
    MAX-ACCESS  accessible-for-notify
    STATUS      current
    DESCRIPTION
        "Logical interface index."
    ::= { gamQosConfigInterfaceSchedulerEntry 1 }

gamQosConfigInterfaceSchedulerQueue OBJECT-TYPE
    SYNTAX      Integer32 (0..7)
    MAX-ACCESS  accessible-for-notify
    STATUS      current
    DESCRIPTION
        "Queue index."
    ::= { gamQosConfigInterfaceSchedulerEntry 2 }

gamQosConfigInterfaceSchedulerWeight OBJECT-TYPE
    SYNTAX      GAMPercent
    MAX-ACCESS  read-write
    STATUS      current
    DESCRIPTION
        "The weight for this queue.
         
         Valid range is 1-100."
    ::= { gamQosConfigInterfaceSchedulerEntry 3 }

gamQosConfigInterfaceSchedulerCutThrough OBJECT-TYPE
    SYNTAX      TruthValue
    MAX-ACCESS  read-write
    STATUS      current
    DESCRIPTION
        "If true, then this queue supports the cut through capability.
         
         Supported only when egress speed is lower or equal to ingress speed.
         
         This object is only available if the capability object
         'gamQosCapabilitiesHasQueueCutThrough' is True."
    ::= { gamQosConfigInterfaceSchedulerEntry 4 }

gamQosConfigInterfaceSchedulerFramePreemption OBJECT-TYPE
    SYNTAX      TruthValue
    MAX-ACCESS  read-write
    STATUS      current
    DESCRIPTION
        "If true, then this queue supports frame preemption capability.
         
         This object is only available if the capability object
         'gamQosCapabilitiesHasQueueFramePreemption' is True."
    ::= { gamQosConfigInterfaceSchedulerEntry 5 }

gamQosConfigInterfaceStormPolicerUnicastTable OBJECT-TYPE
    SYNTAX      SEQUENCE OF GAMQosConfigInterfaceStormPolicerUnicastEntry
    MAX-ACCESS  not-accessible
    STATUS      current
    DESCRIPTION
        "This table provides storm policer configuration for unicast packets
         received on an interface
         
         This is an optional table and is only present if
         qosCapabilitiesHasPortStormPolicers is true."
    ::= { gamQosConfigInterface 9 }

gamQosConfigInterfaceStormPolicerUnicastEntry OBJECT-TYPE
    SYNTAX      GAMQosConfigInterfaceStormPolicerUnicastEntry
    MAX-ACCESS  not-accessible
    STATUS      current
    DESCRIPTION
        "Each row contains the configuration for a specific storm policer"
    INDEX       { gamQosConfigInterfaceStormPolicerUnicastIfIndex }
    ::= { gamQosConfigInterfaceStormPolicerUnicastTable 1 }

GAMQosConfigInterfaceStormPolicerUnicastEntry ::= SEQUENCE {
    gamQosConfigInterfaceStormPolicerUnicastIfIndex    GAMInterfaceIndex,
    gamQosConfigInterfaceStormPolicerUnicastEnable     TruthValue,
    gamQosConfigInterfaceStormPolicerUnicastFrameRate  TruthValue,
    gamQosConfigInterfaceStormPolicerUnicastCir        Unsigned32
}

gamQosConfigInterfaceStormPolicerUnicastIfIndex OBJECT-TYPE
    SYNTAX      GAMInterfaceIndex
    MAX-ACCESS  accessible-for-notify
    STATUS      current
    DESCRIPTION
        "Logical interface index.
         
         This object is only available if the capability object
         'gamQosCapabilitiesHasPortStormPolicers' is True."
    ::= { gamQosConfigInterfaceStormPolicerUnicastEntry 1 }

gamQosConfigInterfaceStormPolicerUnicastEnable OBJECT-TYPE
    SYNTAX      TruthValue
    MAX-ACCESS  read-write
    STATUS      current
    DESCRIPTION
        "If true, the storm policer is enabled.
         
         
         
         This object is only available if the capability object
         'gamQosCapabilitiesHasPortStormPolicers' is True."
    ::= { gamQosConfigInterfaceStormPolicerUnicastEntry 2 }

gamQosConfigInterfaceStormPolicerUnicastFrameRate OBJECT-TYPE
    SYNTAX      TruthValue
    MAX-ACCESS  read-write
    STATUS      current
    DESCRIPTION
        "If true, the rate is measured in fps instead of kbps.
         
         
         
         This object is only available if the capability object
         'gamQosCapabilitiesHasPortStormPolicers' is True."
    ::= { gamQosConfigInterfaceStormPolicerUnicastEntry 3 }

gamQosConfigInterfaceStormPolicerUnicastCir OBJECT-TYPE
    SYNTAX      Unsigned32
    MAX-ACCESS  read-write
    STATUS      current
    DESCRIPTION
        "Committed Information Rate. Measured in kbps if FrameRate is false and
         fps if FrameRate is true.
         
         Valid range is from the smallest value of
         qosCapabilitiesPortStormBitRateMin and
         qosCapabilitiesPortStormFrameRateMin to the largest value of
         qosCapabilitiesPortStormBitRateMax and
         qosCapabilitiesPortStormFrameRateMax.
         
         
         
         This object is only available if the capability object
         'gamQosCapabilitiesHasPortStormPolicers' is True."
    ::= { gamQosConfigInterfaceStormPolicerUnicastEntry 4 }

gamQosConfigInterfaceStormPolicerBroadcastTable OBJECT-TYPE
    SYNTAX      SEQUENCE OF GAMQosConfigInterfaceStormPolicerBroadcastEntry
    MAX-ACCESS  not-accessible
    STATUS      current
    DESCRIPTION
        "This table provides storm policer configuration for broadcast packets
         received on an interface
         
         This is an optional table and is only present if
         qosCapabilitiesHasPortStormPolicers is true."
    ::= { gamQosConfigInterface 10 }

gamQosConfigInterfaceStormPolicerBroadcastEntry OBJECT-TYPE
    SYNTAX      GAMQosConfigInterfaceStormPolicerBroadcastEntry
    MAX-ACCESS  not-accessible
    STATUS      current
    DESCRIPTION
        "Each row contains the configuration for a specific storm policer"
    INDEX       { gamQosConfigInterfaceStormPolicerBroadcastIfIndex }
    ::= { gamQosConfigInterfaceStormPolicerBroadcastTable 1 }

GAMQosConfigInterfaceStormPolicerBroadcastEntry ::= SEQUENCE {
    gamQosConfigInterfaceStormPolicerBroadcastIfIndex    GAMInterfaceIndex,
    gamQosConfigInterfaceStormPolicerBroadcastEnable     TruthValue,
    gamQosConfigInterfaceStormPolicerBroadcastFrameRate  TruthValue,
    gamQosConfigInterfaceStormPolicerBroadcastCir        Unsigned32
}

gamQosConfigInterfaceStormPolicerBroadcastIfIndex OBJECT-TYPE
    SYNTAX      GAMInterfaceIndex
    MAX-ACCESS  accessible-for-notify
    STATUS      current
    DESCRIPTION
        "Logical interface index.
         
         This object is only available if the capability object
         'gamQosCapabilitiesHasPortStormPolicers' is True."
    ::= { gamQosConfigInterfaceStormPolicerBroadcastEntry 1 }

gamQosConfigInterfaceStormPolicerBroadcastEnable OBJECT-TYPE
    SYNTAX      TruthValue
    MAX-ACCESS  read-write
    STATUS      current
    DESCRIPTION
        "If true, the storm policer is enabled.
         
         
         
         This object is only available if the capability object
         'gamQosCapabilitiesHasPortStormPolicers' is True."
    ::= { gamQosConfigInterfaceStormPolicerBroadcastEntry 2 }

gamQosConfigInterfaceStormPolicerBroadcastFrameRate OBJECT-TYPE
    SYNTAX      TruthValue
    MAX-ACCESS  read-write
    STATUS      current
    DESCRIPTION
        "If true, the rate is measured in fps instead of kbps.
         
         
         
         This object is only available if the capability object
         'gamQosCapabilitiesHasPortStormPolicers' is True."
    ::= { gamQosConfigInterfaceStormPolicerBroadcastEntry 3 }

gamQosConfigInterfaceStormPolicerBroadcastCir OBJECT-TYPE
    SYNTAX      Unsigned32
    MAX-ACCESS  read-write
    STATUS      current
    DESCRIPTION
        "Committed Information Rate. Measured in kbps if FrameRate is false and
         fps if FrameRate is true.
         
         Valid range is from the smallest value of
         qosCapabilitiesPortStormBitRateMin and
         qosCapabilitiesPortStormFrameRateMin to the largest value of
         qosCapabilitiesPortStormBitRateMax and
         qosCapabilitiesPortStormFrameRateMax.
         
         
         
         This object is only available if the capability object
         'gamQosCapabilitiesHasPortStormPolicers' is True."
    ::= { gamQosConfigInterfaceStormPolicerBroadcastEntry 4 }

gamQosConfigInterfaceStormPolicerUnknownTable OBJECT-TYPE
    SYNTAX      SEQUENCE OF GAMQosConfigInterfaceStormPolicerUnknownEntry
    MAX-ACCESS  not-accessible
    STATUS      current
    DESCRIPTION
        "This table provides storm policer configuration for unknown (flooded)
         packets received on an interface
         
         This is an optional table and is only present if
         qosCapabilitiesHasPortStormPolicers is true."
    ::= { gamQosConfigInterface 11 }

gamQosConfigInterfaceStormPolicerUnknownEntry OBJECT-TYPE
    SYNTAX      GAMQosConfigInterfaceStormPolicerUnknownEntry
    MAX-ACCESS  not-accessible
    STATUS      current
    DESCRIPTION
        "Each row contains the configuration for a specific storm policer"
    INDEX       { gamQosConfigInterfaceStormPolicerUnknownIfIndex }
    ::= { gamQosConfigInterfaceStormPolicerUnknownTable 1 }

GAMQosConfigInterfaceStormPolicerUnknownEntry ::= SEQUENCE {
    gamQosConfigInterfaceStormPolicerUnknownIfIndex    GAMInterfaceIndex,
    gamQosConfigInterfaceStormPolicerUnknownEnable     TruthValue,
    gamQosConfigInterfaceStormPolicerUnknownFrameRate  TruthValue,
    gamQosConfigInterfaceStormPolicerUnknownCir        Unsigned32
}

gamQosConfigInterfaceStormPolicerUnknownIfIndex OBJECT-TYPE
    SYNTAX      GAMInterfaceIndex
    MAX-ACCESS  accessible-for-notify
    STATUS      current
    DESCRIPTION
        "Logical interface index.
         
         This object is only available if the capability object
         'gamQosCapabilitiesHasPortStormPolicers' is True."
    ::= { gamQosConfigInterfaceStormPolicerUnknownEntry 1 }

gamQosConfigInterfaceStormPolicerUnknownEnable OBJECT-TYPE
    SYNTAX      TruthValue
    MAX-ACCESS  read-write
    STATUS      current
    DESCRIPTION
        "If true, the storm policer is enabled.
         
         
         
         This object is only available if the capability object
         'gamQosCapabilitiesHasPortStormPolicers' is True."
    ::= { gamQosConfigInterfaceStormPolicerUnknownEntry 2 }

gamQosConfigInterfaceStormPolicerUnknownFrameRate OBJECT-TYPE
    SYNTAX      TruthValue
    MAX-ACCESS  read-write
    STATUS      current
    DESCRIPTION
        "If true, the rate is measured in fps instead of kbps.
         
         
         
         This object is only available if the capability object
         'gamQosCapabilitiesHasPortStormPolicers' is True."
    ::= { gamQosConfigInterfaceStormPolicerUnknownEntry 3 }

gamQosConfigInterfaceStormPolicerUnknownCir OBJECT-TYPE
    SYNTAX      Unsigned32
    MAX-ACCESS  read-write
    STATUS      current
    DESCRIPTION
        "Committed Information Rate. Measured in kbps if FrameRate is false and
         fps if FrameRate is true.
         
         Valid range is from the smallest value of
         qosCapabilitiesPortStormBitRateMin and
         qosCapabilitiesPortStormFrameRateMin to the largest value of
         qosCapabilitiesPortStormBitRateMax and
         qosCapabilitiesPortStormFrameRateMax.
         
         
         
         This object is only available if the capability object
         'gamQosCapabilitiesHasPortStormPolicers' is True."
    ::= { gamQosConfigInterfaceStormPolicerUnknownEntry 4 }

gamQosConfigInterfaceQbvMaxSduTable OBJECT-TYPE
    SYNTAX      SEQUENCE OF GAMQosConfigInterfaceQbvMaxSduEntry
    MAX-ACCESS  not-accessible
    STATUS      current
    DESCRIPTION
        "A table containing a set of max SDU parameters, one for each traffic
         class.
         
         All writeable objects in this table must be persistent over power up
         restart/reboot.
         
         "
    ::= { gamQosConfigInterface 12 }

gamQosConfigInterfaceQbvMaxSduEntry OBJECT-TYPE
    SYNTAX      GAMQosConfigInterfaceQbvMaxSduEntry
    MAX-ACCESS  not-accessible
    STATUS      current
    DESCRIPTION
        "Each row contains the maximum SDU value for a specific queue."
    INDEX       { gamQosConfigInterfaceQbvMaxSduIfIndex,
                  gamQosConfigInterfaceQbvMaxSduQueue }
    ::= { gamQosConfigInterfaceQbvMaxSduTable 1 }

GAMQosConfigInterfaceQbvMaxSduEntry ::= SEQUENCE {
    gamQosConfigInterfaceQbvMaxSduIfIndex  GAMInterfaceIndex,
    gamQosConfigInterfaceQbvMaxSduQueue    Integer32,
    gamQosConfigInterfaceQbvMaxSduMaxSDU   GAMUnsigned16
}

gamQosConfigInterfaceQbvMaxSduIfIndex OBJECT-TYPE
    SYNTAX      GAMInterfaceIndex
    MAX-ACCESS  accessible-for-notify
    STATUS      current
    DESCRIPTION
        "Logical interface index.
         
         This object is only available if the capability object
         'gamQosCapabilitiesHasQbv' is True."
    ::= { gamQosConfigInterfaceQbvMaxSduEntry 1 }

gamQosConfigInterfaceQbvMaxSduQueue OBJECT-TYPE
    SYNTAX      Integer32 (0..7)
    MAX-ACCESS  accessible-for-notify
    STATUS      current
    DESCRIPTION
        "Queue index.
         
         This object is only available if the capability object
         'gamQosCapabilitiesHasQbv' is True."
    ::= { gamQosConfigInterfaceQbvMaxSduEntry 2 }

gamQosConfigInterfaceQbvMaxSduMaxSDU OBJECT-TYPE
    SYNTAX      GAMUnsigned16
    MAX-ACCESS  read-write
    STATUS      current
    DESCRIPTION
        "The value of the MaxSDU parameter for the traffic class.
         
         This value is represented as an unsigned integer. A value
         
         of 0 is interpreted as the max SDU size supported by
         
         the underlying MAC.
         
         The default value of the MaxSDU parameter is 0.
         
         The value of this object MUST be retained across
         
         reinitializations of the management system.
         
         
         
         This object is only available if the capability object
         'gamQosCapabilitiesHasQbv' is True."
    ::= { gamQosConfigInterfaceQbvMaxSduEntry 3 }

gamQosConfigInterfaceQbvGclAdminTable OBJECT-TYPE
    SYNTAX      SEQUENCE OF GAMQosConfigInterfaceQbvGclAdminEntry
    MAX-ACCESS  not-accessible
    STATUS      current
    DESCRIPTION
        "A table containing the admin entries/TLVs of the GCL, as defined in
         IEEE 802.1Qbv"
    ::= { gamQosConfigInterface 13 }

gamQosConfigInterfaceQbvGclAdminEntry OBJECT-TYPE
    SYNTAX      GAMQosConfigInterfaceQbvGclAdminEntry
    MAX-ACCESS  not-accessible
    STATUS      current
    DESCRIPTION
        "Each row contains single GCL entry with a unique gcl_index"
    INDEX       { gamQosConfigInterfaceQbvGclAdminIfIndex,
                  gamQosConfigInterfaceQbvGclAdminGclIndex }
    ::= { gamQosConfigInterfaceQbvGclAdminTable 1 }

GAMQosConfigInterfaceQbvGclAdminEntry ::= SEQUENCE {
    gamQosConfigInterfaceQbvGclAdminIfIndex       GAMInterfaceIndex,
    gamQosConfigInterfaceQbvGclAdminGclIndex      Integer32,
    gamQosConfigInterfaceQbvGclAdminGateState     OCTET STRING,
    gamQosConfigInterfaceQbvGclAdminTimeInterval  Unsigned32
}

gamQosConfigInterfaceQbvGclAdminIfIndex OBJECT-TYPE
    SYNTAX      GAMInterfaceIndex
    MAX-ACCESS  accessible-for-notify
    STATUS      current
    DESCRIPTION
        "Logical interface index.
         
         This object is only available if the capability object
         'gamQosCapabilitiesHasQbv' is True."
    ::= { gamQosConfigInterfaceQbvGclAdminEntry 1 }

gamQosConfigInterfaceQbvGclAdminGclIndex OBJECT-TYPE
    SYNTAX      Integer32 (0..63)
    MAX-ACCESS  accessible-for-notify
    STATUS      current
    DESCRIPTION
        "Gate control list index.
         
         This object is only available if the capability object
         'gamQosCapabilitiesHasQbv' is True."
    ::= { gamQosConfigInterfaceQbvGclAdminEntry 2 }

gamQosConfigInterfaceQbvGclAdminGateState OBJECT-TYPE
    SYNTAX      OCTET STRING (SIZE(1))
    MAX-ACCESS  read-write
    STATUS      current
    DESCRIPTION
        "A GateState parameter is encoded in a single octet.
         
         The bits of the octet represent the gate states for the
         
         corresponding traffic classes;the MS bit corresponds to
         
         traffic class 7, the LS bit to traffic class 0.
         
         A bit value of 0 indicates closed;a
         
         bit value of 1 indicates open.
         
         
         
         This object is only available if the capability object
         'gamQosCapabilitiesHasQbv' is True."
    ::= { gamQosConfigInterfaceQbvGclAdminEntry 3 }

gamQosConfigInterfaceQbvGclAdminTimeInterval OBJECT-TYPE
    SYNTAX      Unsigned32
    MAX-ACCESS  read-write
    STATUS      current
    DESCRIPTION
        "A TimeInterval is encoded in 4 octets as a 32-bit
         
         unsigned integer, representing
         
         a number of nanoseconds. The first octet encodes the
         
         most significant 8 bits of the integer, and the fourth
         
         octet encodes the least significant 8 bits.
         
         
         
         This object is only available if the capability object
         'gamQosCapabilitiesHasQbv' is True."
    ::= { gamQosConfigInterfaceQbvGclAdminEntry 4 }

gamQosConfigInterfaceQbvParamsTable OBJECT-TYPE
    SYNTAX      SEQUENCE OF GAMQosConfigInterfaceQbvParamsEntry
    MAX-ACCESS  not-accessible
    STATUS      current
    DESCRIPTION
        "A table that contains the per-port manageable parameters for traffic
         scheduling."
    ::= { gamQosConfigInterface 14 }

gamQosConfigInterfaceQbvParamsEntry OBJECT-TYPE
    SYNTAX      GAMQosConfigInterfaceQbvParamsEntry
    MAX-ACCESS  not-accessible
    STATUS      current
    DESCRIPTION
        "A list of objects that contains the manageable parameters for traffic
         scheduling for a port."
    INDEX       { gamQosConfigInterfaceQbvParamsIfIndex }
    ::= { gamQosConfigInterfaceQbvParamsTable 1 }

GAMQosConfigInterfaceQbvParamsEntry ::= SEQUENCE {
    gamQosConfigInterfaceQbvParamsIfIndex                    GAMInterfaceIndex,
    gamQosConfigInterfaceQbvParamsGateEnabled                TruthValue,
    gamQosConfigInterfaceQbvParamsAdminGateStates            OCTET STRING,
    gamQosConfigInterfaceQbvParamsAdminControlListLength     Unsigned32,
    gamQosConfigInterfaceQbvParamsAdminCycleTimeNumerator    Unsigned32,
    gamQosConfigInterfaceQbvParamsAdminCycleTimeDenominator  Unsigned32,
    gamQosConfigInterfaceQbvParamsAdminCycleTimeExtension    Unsigned32,
    gamQosConfigInterfaceQbvParamsAdminBaseTimeSecs          Unsigned32,
    gamQosConfigInterfaceQbvParamsAdminBaseTimeNanoSecs      Unsigned32,
    gamQosConfigInterfaceQbvParamsConfigChange               TruthValue
}

gamQosConfigInterfaceQbvParamsIfIndex OBJECT-TYPE
    SYNTAX      GAMInterfaceIndex
    MAX-ACCESS  accessible-for-notify
    STATUS      current
    DESCRIPTION
        "Logical interface index.
         
         This object is only available if the capability object
         'gamQosCapabilitiesHasQbv' is True."
    ::= { gamQosConfigInterfaceQbvParamsEntry 1 }

gamQosConfigInterfaceQbvParamsGateEnabled OBJECT-TYPE
    SYNTAX      TruthValue
    MAX-ACCESS  read-write
    STATUS      current
    DESCRIPTION
        "The GateEnabled parameter determines whether traffic scheduling
         
         is active (true) or inactive (false).
         
         The value of this object MUST be retained across
         
         reinitializations of the management system.
         
         
         
         This object is only available if the capability object
         'gamQosCapabilitiesHasQbv' is True."
    ::= { gamQosConfigInterfaceQbvParamsEntry 2 }

gamQosConfigInterfaceQbvParamsAdminGateStates OBJECT-TYPE
    SYNTAX      OCTET STRING (SIZE(1))
    MAX-ACCESS  read-write
    STATUS      current
    DESCRIPTION
        "The administrative value of the GateStates parameter for the Port.
         
         The bits of the octet represent the gate states for the
         
         corresponding traffic classes;the MS bit corresponds to traffic class
         7,
         
         the LS bit to traffic class 0. A bit value of 0 indicates closed; a
         
         bit value of 1 indicates open.
         
         The value of this object MUST be retained across
         
         reinitializations of the management system.
         
         
         
         This object is only available if the capability object
         'gamQosCapabilitiesHasQbv' is True."
    ::= { gamQosConfigInterfaceQbvParamsEntry 3 }

gamQosConfigInterfaceQbvParamsAdminControlListLength OBJECT-TYPE
    SYNTAX      Unsigned32
    MAX-ACCESS  read-write
    STATUS      current
    DESCRIPTION
        "The administrative value of the ListMax parameter for the Port.
         
         The integer value indicates the number of entries (TLVs) in the
         
         AdminControlList.
         
         The value of this object MUST be retained across
         
         reinitializations of the management system.
         
         
         
         This object is only available if the capability object
         'gamQosCapabilitiesHasQbv' is True."
    ::= { gamQosConfigInterfaceQbvParamsEntry 4 }

gamQosConfigInterfaceQbvParamsAdminCycleTimeNumerator OBJECT-TYPE
    SYNTAX      Unsigned32
    MAX-ACCESS  read-write
    STATUS      current
    DESCRIPTION
        "The administrative value of the numerator of the CycleTime
         
         parameter for the Port.
         
         The numerator and denominator together represent the cycle time as
         
         a rational number of seconds.
         
         The value of this object MUST be retained across
         
         reinitializations of the management system
         
         
         
         This object is only available if the capability object
         'gamQosCapabilitiesHasQbv' is True."
    ::= { gamQosConfigInterfaceQbvParamsEntry 5 }

gamQosConfigInterfaceQbvParamsAdminCycleTimeDenominator OBJECT-TYPE
    SYNTAX      Unsigned32
    MAX-ACCESS  read-write
    STATUS      current
    DESCRIPTION
        "The administrative value of the denominator of the
         
         CycleTime parameter for the Port.
         
         The numerator and denominator together represent the cycle time as
         
         a rational number of seconds.
         
         The value of this object MUST be retained across
         
         reinitializations of the management system.
         
         
         
         This object is only available if the capability object
         'gamQosCapabilitiesHasQbv' is True."
    ::= { gamQosConfigInterfaceQbvParamsEntry 6 }

gamQosConfigInterfaceQbvParamsAdminCycleTimeExtension OBJECT-TYPE
    SYNTAX      Unsigned32
    MAX-ACCESS  read-write
    STATUS      current
    DESCRIPTION
        "The administrative value of the CycleTimeExtension
         
         parameter for the Port.
         
         The value is an unsigned integer number of nanoseconds.
         
         The value of this object MUST be retained across
         
         reinitializations of the management system.
         
         
         
         This object is only available if the capability object
         'gamQosCapabilitiesHasQbv' is True."
    ::= { gamQosConfigInterfaceQbvParamsEntry 7 }

gamQosConfigInterfaceQbvParamsAdminBaseTimeSecs OBJECT-TYPE
    SYNTAX      Unsigned32
    MAX-ACCESS  read-write
    STATUS      current
    DESCRIPTION
        "The administrative value of the BaseTime parameter for the Port.
         
         The value is a representation of a PTPtime value,
         
         consisting of a 48-bit integer
         
         number of seconds and a 32-bit integer number of nanoseconds.
         
         The value of this object MUST be retained across
         
         reinitializations of the management system.
         
         
         
         This object is only available if the capability object
         'gamQosCapabilitiesHasQbv' is True."
    ::= { gamQosConfigInterfaceQbvParamsEntry 8 }

gamQosConfigInterfaceQbvParamsAdminBaseTimeNanoSecs OBJECT-TYPE
    SYNTAX      Unsigned32
    MAX-ACCESS  read-write
    STATUS      current
    DESCRIPTION
        "The administrative value of the BaseTime parameter for the Port.
         
         The value is a representation of a PTPtime value,
         
         consisting of a 48-bit integer
         
         number of seconds and a 32-bit integer number of nanoseconds.
         
         The value of this object MUST be retained across
         
         reinitializations of the management system.
         
         
         
         This object is only available if the capability object
         'gamQosCapabilitiesHasQbv' is True."
    ::= { gamQosConfigInterfaceQbvParamsEntry 9 }

gamQosConfigInterfaceQbvParamsConfigChange OBJECT-TYPE
    SYNTAX      TruthValue
    MAX-ACCESS  read-write
    STATUS      current
    DESCRIPTION
        "The ConfigChange parameter signals the start of a
         
         configuration change
         
         when it is set to TRUE. This should only be done
         
         when the various administrative parameters
         
         are all set to appropriate values.
         
         
         
         This object is only available if the capability object
         'gamQosCapabilitiesHasQbv' is True."
    ::= { gamQosConfigInterfaceQbvParamsEntry 10 }

gamQosConfigInterfaceFpTable OBJECT-TYPE
    SYNTAX      SEQUENCE OF GAMQosConfigInterfaceFpEntry
    MAX-ACCESS  not-accessible
    STATUS      current
    DESCRIPTION
        "A table that contains the per-port frame preemption configuration."
    ::= { gamQosConfigInterface 15 }

gamQosConfigInterfaceFpEntry OBJECT-TYPE
    SYNTAX      GAMQosConfigInterfaceFpEntry
    MAX-ACCESS  not-accessible
    STATUS      current
    DESCRIPTION
        "A list of objects that contains the frame preemption configuration for
         a port."
    INDEX       { gamQosConfigInterfaceFpIfIndex }
    ::= { gamQosConfigInterfaceFpTable 1 }

GAMQosConfigInterfaceFpEntry ::= SEQUENCE {
    gamQosConfigInterfaceFpIfIndex        GAMInterfaceIndex,
    gamQosConfigInterfaceFpEnableTx       TruthValue,
    gamQosConfigInterfaceFpVerifyDisable  TruthValue
}

gamQosConfigInterfaceFpIfIndex OBJECT-TYPE
    SYNTAX      GAMInterfaceIndex
    MAX-ACCESS  accessible-for-notify
    STATUS      current
    DESCRIPTION
        "Logical interface index.
         
         This object is only available if the capability object
         'gamQosCapabilitiesHasQueueFramePreemption' is True."
    ::= { gamQosConfigInterfaceFpEntry 1 }

gamQosConfigInterfaceFpEnableTx OBJECT-TYPE
    SYNTAX      TruthValue
    MAX-ACCESS  read-write
    STATUS      current
    DESCRIPTION
        "The value of the 802.3br aMACMergeEnableTx parameter for the port. This
         value determines whether frame preemption is enabled (true) or disabled
         (false) in the MAC Merge sublayer in the transmit direction.
         
         This object is only available if the capability object
         'gamQosCapabilitiesHasQueueFramePreemption' is True."
    ::= { gamQosConfigInterfaceFpEntry 2 }

gamQosConfigInterfaceFpVerifyDisable OBJECT-TYPE
    SYNTAX      TruthValue
    MAX-ACCESS  read-write
    STATUS      current
    DESCRIPTION
        "The value of the 802.3br aMACMergeVerifyDisableTx parameter for the
         port. This value determines whether the verifiy function is disabled
         (true) or enabled (false) in the MAC Merge sublayer in the transmit
         direction.
         
         This object is only available if the capability object
         'gamQosCapabilitiesHasQueueFramePreemption' is True."
    ::= { gamQosConfigInterfaceFpEntry 3 }

gamQosConfigQce OBJECT IDENTIFIER
    ::= { gamQosConfig 3 }

gamQosConfigQceTable OBJECT-TYPE
    SYNTAX      SEQUENCE OF GAMQosConfigQceEntry
    MAX-ACCESS  not-accessible
    STATUS      current
    DESCRIPTION
        "This table contains the configuration of QCEs. The index is QceId.
         
         This is an optional table and is only present if qosCapabilitiesHasQce
         is true."
    ::= { gamQosConfigQce 1 }

gamQosConfigQceEntry OBJECT-TYPE
    SYNTAX      GAMQosConfigQceEntry
    MAX-ACCESS  not-accessible
    STATUS      current
    DESCRIPTION
        "Each row contains the configuration of a single QCE."
    INDEX       { gamQosConfigQceQceId }
    ::= { gamQosConfigQceTable 1 }

GAMQosConfigQceEntry ::= SEQUENCE {
    gamQosConfigQceQceId               Integer32,
    gamQosConfigQceNextQceId           Unsigned32,
    gamQosConfigQceSwitchId            Unsigned32,
    gamQosConfigQcePortList            GAMPortList,
    gamQosConfigQceDestMacType         GAMDestMacType,
    gamQosConfigQceDestMac             MacAddress,
    gamQosConfigQceDestMacMask         MacAddress,
    gamQosConfigQceSrcMac              MacAddress,
    gamQosConfigQceSrcMacMask          MacAddress,
    gamQosConfigQceVlanTagType         GAMVlanTagType,
    gamQosConfigQceVlanIdOp            GAMASRType,
    gamQosConfigQceVlanId              GAMUnsigned16,
    gamQosConfigQceVlanIdRange         GAMUnsigned16,
    gamQosConfigQcePcp                 GAMVlanTagPriority,
    gamQosConfigQceDei                 GAMBitType,
    gamQosConfigQceInnerVlanTagType    GAMVlanTagType,
    gamQosConfigQceInnerVlanIdOp       GAMASRType,
    gamQosConfigQceInnerVlanId         GAMUnsigned16,
    gamQosConfigQceInnerVlanIdRange    GAMUnsigned16,
    gamQosConfigQceInnerPcp            GAMVlanTagPriority,
    gamQosConfigQceInnerDei            GAMBitType,
    gamQosConfigQceFrameType           GAMQosQceFrameType,
    gamQosConfigQceEtype               GAMEtherType,
    gamQosConfigQceLlcDsap             GAMUnsigned8,
    gamQosConfigQceLlcDsapMask         GAMUnsigned8,
    gamQosConfigQceLlcSsap             GAMUnsigned8,
    gamQosConfigQceLlcSsapMask         GAMUnsigned8,
    gamQosConfigQceLlcControl          GAMUnsigned8,
    gamQosConfigQceLlcControlMask      GAMUnsigned8,
    gamQosConfigQceSnapPid             GAMUnsigned16,
    gamQosConfigQceSnapPidMask         GAMUnsigned16,
    gamQosConfigQceIpv4Fragment        GAMBitType,
    gamQosConfigQceIpv4DscpOp          GAMASRType,
    gamQosConfigQceIpv4Dscp            Dscp,
    gamQosConfigQceIpv4DscpRange       Dscp,
    gamQosConfigQceIpv4Protocol        GAMUnsigned8,
    gamQosConfigQceIpv4ProtocolMask    GAMUnsigned8,
    gamQosConfigQceIpv4SrcIp           IpAddress,
    gamQosConfigQceIpv4SrcIpMask       IpAddress,
    gamQosConfigQceIpv4DestIp          IpAddress,
    gamQosConfigQceIpv4DestIpMask      IpAddress,
    gamQosConfigQceIpv4SrcPortOp       GAMASRType,
    gamQosConfigQceIpv4SrcPort         GAMUnsigned16,
    gamQosConfigQceIpv4SrcPortRange    GAMUnsigned16,
    gamQosConfigQceIpv4DestPortOp      GAMASRType,
    gamQosConfigQceIpv4DestPort        GAMUnsigned16,
    gamQosConfigQceIpv4DestPortRange   GAMUnsigned16,
    gamQosConfigQceIpv6DscpOp          GAMASRType,
    gamQosConfigQceIpv6Dscp            Dscp,
    gamQosConfigQceIpv6DscpRange       Dscp,
    gamQosConfigQceIpv6Protocol        GAMUnsigned8,
    gamQosConfigQceIpv6ProtocolMask    GAMUnsigned8,
    gamQosConfigQceIpv6SrcIp           InetAddressIPv6,
    gamQosConfigQceIpv6SrcIpMask       InetAddressIPv6,
    gamQosConfigQceIpv6DestIp          InetAddressIPv6,
    gamQosConfigQceIpv6DestIpMask      InetAddressIPv6,
    gamQosConfigQceIpv6SrcPortOp       GAMASRType,
    gamQosConfigQceIpv6SrcPort         GAMUnsigned16,
    gamQosConfigQceIpv6SrcPortRange    GAMUnsigned16,
    gamQosConfigQceIpv6DestPortOp      GAMASRType,
    gamQosConfigQceIpv6DestPort        GAMUnsigned16,
    gamQosConfigQceIpv6DestPortRange   GAMUnsigned16,
    gamQosConfigQceActionCosEnable     TruthValue,
    gamQosConfigQceActionCos           Unsigned32,
    gamQosConfigQceActionDplEnable     TruthValue,
    gamQosConfigQceActionDpl           GAMUnsigned8,
    gamQosConfigQceActionDscpEnable    TruthValue,
    gamQosConfigQceActionDscp          GAMUnsigned8,
    gamQosConfigQceActionPcpDeiEnable  TruthValue,
    gamQosConfigQceActionPcp           Unsigned32,
    gamQosConfigQceActionDei           GAMUnsigned8,
    gamQosConfigQceActionPolicyEnable  TruthValue,
    gamQosConfigQceActionPolicy        Unsigned32,
    gamQosConfigQceActionMapEnable     TruthValue,
    gamQosConfigQceActionMap           GAMUnsigned16,
    gamQosConfigQceAction              GAMRowEditorState
}

gamQosConfigQceQceId OBJECT-TYPE
    SYNTAX      Integer32 (0..2147483647)
    MAX-ACCESS  accessible-for-notify
    STATUS      current
    DESCRIPTION
        "QCE Id.
         
         Valid range is qosCapabilitiesQceIdMin-qosCapabilitiesQceIdMax or 0.
         
         Using a value of 0 when adding a new QCE, will assign the QCE Id in the
         new QCE to the first unused QCE Id.
         
         This object is only available if the capability object
         'gamQosCapabilitiesHasQce' is True."
    ::= { gamQosConfigQceEntry 1 }

gamQosConfigQceNextQceId OBJECT-TYPE
    SYNTAX      Unsigned32
    MAX-ACCESS  read-write
    STATUS      current
    DESCRIPTION
        "QCE Id of the next QCE. Valid range is
         qosCapabilitiesQceIdMin-qosCapabilitiesQceIdMax or 0.
         
         The value 0, denotes the end of the list.
         
         This object is only available if the capability object
         'gamQosCapabilitiesHasQce' is True."
    ::= { gamQosConfigQceEntry 2 }

gamQosConfigQceSwitchId OBJECT-TYPE
    SYNTAX      Unsigned32
    MAX-ACCESS  read-write
    STATUS      current
    DESCRIPTION
        "Indicates the switch on which this QCE is active.Valid range is
         documented in the Stacking MIB.
         
         This object is only valid on stacking platforms.
         
         This object is only available if the capability object
         'gamQosCapabilitiesHasQce' is True."
    ::= { gamQosConfigQceEntry 3 }

gamQosConfigQcePortList OBJECT-TYPE
    SYNTAX      GAMPortList
    MAX-ACCESS  read-write
    STATUS      current
    DESCRIPTION
        "List of ports that are member of this QCE.
         
         This object is only available if the capability object
         'gamQosCapabilitiesHasQce' is True."
    ::= { gamQosConfigQceEntry 4 }

gamQosConfigQceDestMacType OBJECT-TYPE
    SYNTAX      GAMDestMacType
    MAX-ACCESS  read-write
    STATUS      current
    DESCRIPTION
        "Indicates the destination MAC type to match.
         
         This object is only available if the capability object
         'gamQosCapabilitiesHasQce' is True."
    ::= { gamQosConfigQceEntry 5 }

gamQosConfigQceDestMac OBJECT-TYPE
    SYNTAX      MacAddress
    MAX-ACCESS  read-write
    STATUS      current
    DESCRIPTION
        "Indicates the 48 bits destination MAC address.
         
         The packet's destination address is AND-ed with the value of
         DestMacMask and then compared against the value of this object.
         
         If this object value and the value of DestMacMask is 00-00-00-00-00-00,
         this entry matches any destination MAC address.
         
         This object can only be configured if DestMacType is any(0) and
         DestMacMask is ff-ff-ff-ff-ff-ff.
         
         
         
         This object is only available if the capability object
         'gamQosCapabilitiesHasQceDmac' is True."
    ::= { gamQosConfigQceEntry 6 }

gamQosConfigQceDestMacMask OBJECT-TYPE
    SYNTAX      MacAddress
    MAX-ACCESS  read-write
    STATUS      current
    DESCRIPTION
        "Indicates the 48 bits destination MAC address mask.
         
         Valid values are 00-00-00-00-00-00 or ff-ff-ff-ff-ff-ff.
         
         
         
         This object is only available if the capability object
         'gamQosCapabilitiesHasQceDmac' is True."
    ::= { gamQosConfigQceEntry 7 }

gamQosConfigQceSrcMac OBJECT-TYPE
    SYNTAX      MacAddress
    MAX-ACCESS  read-write
    STATUS      current
    DESCRIPTION
        "Indicates the 48 bits source MAC address.
         
         The packet's source address is AND-ed with the value of SrcMacMask and
         then compared against the value of this object.
         
         If this object value and the value of SrcMacMask is 00-00-00-00-00-00,
         this entry matches any source MAC address.
         
         This object can only be configured if SrcMacMask is ff-ff-ff-ff-ff-ff.
         
         If the value of qosCapabilitiesHasQceMacOui is true then only the OUI
         part of the MAC address (24 most significant bits) is used.
         
         This object is only available if the capability object
         'gamQosCapabilitiesHasQce' is True."
    ::= { gamQosConfigQceEntry 8 }

gamQosConfigQceSrcMacMask OBJECT-TYPE
    SYNTAX      MacAddress
    MAX-ACCESS  read-write
    STATUS      current
    DESCRIPTION
        "Indicates the 48 bits source MAC address mask.
         
         Valid values are 00-00-00-00-00-00 or ff-ff-ff-ff-ff-ff.
         
         This object is only available if the capability object
         'gamQosCapabilitiesHasQce' is True."
    ::= { gamQosConfigQceEntry 9 }

gamQosConfigQceVlanTagType OBJECT-TYPE
    SYNTAX      GAMVlanTagType
    MAX-ACCESS  read-write
    STATUS      current
    DESCRIPTION
        "Indicates the VLAN tag type to match.
         
         The value cTagged(3) is only supported if qosCapabilitiesHasQceCTag is
         true.
         
         The value sTagged(3) is only supported if qosCapabilitiesHasQceSTag is
         true.
         
         This object is only available if the capability object
         'gamQosCapabilitiesHasQce' is True."
    ::= { gamQosConfigQceEntry 10 }

gamQosConfigQceVlanIdOp OBJECT-TYPE
    SYNTAX      GAMASRType
    MAX-ACCESS  read-write
    STATUS      current
    DESCRIPTION
        "Indicates how a packets's VLAN ID is to be compared.
         
         This object is only available if the capability object
         'gamQosCapabilitiesHasQce' is True."
    ::= { gamQosConfigQceEntry 11 }

gamQosConfigQceVlanId OBJECT-TYPE
    SYNTAX      GAMUnsigned16
    MAX-ACCESS  read-write
    STATUS      current
    DESCRIPTION
        "The VLAN ID to be compared.
         
         If the VlanIdOp object in the same row is range(2), this object will be
         the starting VLAN ID of the range.
         
         Valid range is 0-4095.
         
         This object can only be configured if VlanIdOp is not any(0).
         
         This object is only available if the capability object
         'gamQosCapabilitiesHasQce' is True."
    ::= { gamQosConfigQceEntry 12 }

gamQosConfigQceVlanIdRange OBJECT-TYPE
    SYNTAX      GAMUnsigned16
    MAX-ACCESS  read-write
    STATUS      current
    DESCRIPTION
        "The VLAN ID to be compared.
         
         If the VlanIdOp object in the same row is range(2), this object will be
         the ending VLAN ID of the range.
         
         Valid range is 0-4095.
         
         This object can only be configured if VlanIdOp is range(2).
         
         This object is only available if the capability object
         'gamQosCapabilitiesHasQce' is True."
    ::= { gamQosConfigQceEntry 13 }

gamQosConfigQcePcp OBJECT-TYPE
    SYNTAX      GAMVlanTagPriority
    MAX-ACCESS  read-write
    STATUS      current
    DESCRIPTION
        "The PCP value(s) to be compared.
         
         This object is only available if the capability object
         'gamQosCapabilitiesHasQce' is True."
    ::= { gamQosConfigQceEntry 14 }

gamQosConfigQceDei OBJECT-TYPE
    SYNTAX      GAMBitType
    MAX-ACCESS  read-write
    STATUS      current
    DESCRIPTION
        "The DEI value to be compared.
         
         Valid range is 0-1.
         
         This object is only available if the capability object
         'gamQosCapabilitiesHasQce' is True."
    ::= { gamQosConfigQceEntry 15 }

gamQosConfigQceInnerVlanTagType OBJECT-TYPE
    SYNTAX      GAMVlanTagType
    MAX-ACCESS  read-write
    STATUS      current
    DESCRIPTION
        "Indicates the inner VLAN tag type to match.
         
         
         
         This object is only available if the capability object
         'gamQosCapabilitiesHasQceInnerTag' is True."
    ::= { gamQosConfigQceEntry 16 }

gamQosConfigQceInnerVlanIdOp OBJECT-TYPE
    SYNTAX      GAMASRType
    MAX-ACCESS  read-write
    STATUS      current
    DESCRIPTION
        "Indicates how a packets's inner VLAN ID is to be compared.
         
         
         
         This object is only available if the capability object
         'gamQosCapabilitiesHasQceInnerTag' is True."
    ::= { gamQosConfigQceEntry 17 }

gamQosConfigQceInnerVlanId OBJECT-TYPE
    SYNTAX      GAMUnsigned16
    MAX-ACCESS  read-write
    STATUS      current
    DESCRIPTION
        "The inner VLAN ID to be compared.
         
         If the InnerVlanIdOp object in the same row is range(2), this object
         will be the starting VLAN ID of the range.
         
         Valid range is 0-4095.
         
         This object can only be configured if InnerVlanIdOp is not any(0).
         
         
         
         This object is only available if the capability object
         'gamQosCapabilitiesHasQceInnerTag' is True."
    ::= { gamQosConfigQceEntry 18 }

gamQosConfigQceInnerVlanIdRange OBJECT-TYPE
    SYNTAX      GAMUnsigned16
    MAX-ACCESS  read-write
    STATUS      current
    DESCRIPTION
        "The inner VLAN ID to be compared.
         
         If the InnerVlanIdOp object in the same row is range(2), this object
         will be the ending VLAN ID of the range.
         
         Valid range is 0-4095.
         
         This object can only be configured if InnerVlanIdOp is range(2).
         
         
         
         This object is only available if the capability object
         'gamQosCapabilitiesHasQceInnerTag' is True."
    ::= { gamQosConfigQceEntry 19 }

gamQosConfigQceInnerPcp OBJECT-TYPE
    SYNTAX      GAMVlanTagPriority
    MAX-ACCESS  read-write
    STATUS      current
    DESCRIPTION
        "The inner PCP value(s) to be compared.
         
         
         
         This object is only available if the capability object
         'gamQosCapabilitiesHasQceInnerTag' is True."
    ::= { gamQosConfigQceEntry 20 }

gamQosConfigQceInnerDei OBJECT-TYPE
    SYNTAX      GAMBitType
    MAX-ACCESS  read-write
    STATUS      current
    DESCRIPTION
        "The inner DEI value to be compared.
         
         Valid range is 0-1.
         
         
         
         This object is only available if the capability object
         'gamQosCapabilitiesHasQceInnerTag' is True."
    ::= { gamQosConfigQceEntry 21 }

gamQosConfigQceFrameType OBJECT-TYPE
    SYNTAX      GAMQosQceFrameType
    MAX-ACCESS  read-write
    STATUS      current
    DESCRIPTION
        "Indicates the packet's frame type.
         
         Modifying the frame type on an existing QCE will restore the content of
         all frame type dependent configuration to default.
         
         This object is only available if the capability object
         'gamQosCapabilitiesHasQce' is True."
    ::= { gamQosConfigQceEntry 100 }

gamQosConfigQceEtype OBJECT-TYPE
    SYNTAX      GAMEtherType
    MAX-ACCESS  read-write
    STATUS      current
    DESCRIPTION
        "Indicates the packet's 16 bit Ethernet type field.
         
         Valid values are: 0(match any), 0x600-0xFFFF but excluding 0x800(IPv4)
         and 0x86DD(IPv6).
         
         This object can only be configured if FrameType is etype(1).
         
         This object is only available if the capability object
         'gamQosCapabilitiesHasQce' is True."
    ::= { gamQosConfigQceEntry 101 }

gamQosConfigQceLlcDsap OBJECT-TYPE
    SYNTAX      GAMUnsigned8
    MAX-ACCESS  read-write
    STATUS      current
    DESCRIPTION
        "Indicates the packets's 8 bit LLC DSAP field.
         
         The packet's LLC DSAP field is AND-ed with the value of LlcDsapMask and
         then compared against the value of this object.
         
         If this object value and the value of LlcDsapMask is 0x00, this entry
         matches any LLC DSAP.
         
         Valid range is 0x00-0xFF.
         
         This object can only be configured if FrameType is llc(2).
         
         This object is only available if the capability object
         'gamQosCapabilitiesHasQce' is True."
    ::= { gamQosConfigQceEntry 200 }

gamQosConfigQceLlcDsapMask OBJECT-TYPE
    SYNTAX      GAMUnsigned8
    MAX-ACCESS  read-write
    STATUS      current
    DESCRIPTION
        "Indicates the 8 bit LLC DSAP mask.
         
         Valid values are 0x00 or 0xFF.
         
         This object can only be configured if FrameType is llc(2).
         
         This object is only available if the capability object
         'gamQosCapabilitiesHasQce' is True."
    ::= { gamQosConfigQceEntry 201 }

gamQosConfigQceLlcSsap OBJECT-TYPE
    SYNTAX      GAMUnsigned8
    MAX-ACCESS  read-write
    STATUS      current
    DESCRIPTION
        "Indicates the packets's 8 bit LLC SSAP field.
         
         The packet's LLC SSAP field is AND-ed with the value of LlcSsapMask and
         then compared against the value of this object.
         
         If this object value and the value of LlcSsapMask is 0x00, this entry
         matches any LLC SSAP.
         
         Valid range is 0x00-0xFF.
         
         This object can only be configured if FrameType is llc(2).
         
         This object is only available if the capability object
         'gamQosCapabilitiesHasQce' is True."
    ::= { gamQosConfigQceEntry 202 }

gamQosConfigQceLlcSsapMask OBJECT-TYPE
    SYNTAX      GAMUnsigned8
    MAX-ACCESS  read-write
    STATUS      current
    DESCRIPTION
        "Indicates the 8 bit LLC SSAP mask.
         
         Valid values are 0x00 or 0xFF.
         
         This object can only be configured if FrameType is llc(2).
         
         This object is only available if the capability object
         'gamQosCapabilitiesHasQce' is True."
    ::= { gamQosConfigQceEntry 203 }

gamQosConfigQceLlcControl OBJECT-TYPE
    SYNTAX      GAMUnsigned8
    MAX-ACCESS  read-write
    STATUS      current
    DESCRIPTION
        "Indicates the packets's 8 bit LLC Control field.
         
         The packet's LLC Control field is AND-ed with the value of
         LlcControlMask and then compared against the value of this object.
         
         If this object value and the value of LlcControlMask is 0x00, this
         entry matches any LLC Control.
         
         Valid range is 0x00-0xFF.
         
         This object can only be configured if FrameType is llc(2).
         
         This object is only available if the capability object
         'gamQosCapabilitiesHasQce' is True."
    ::= { gamQosConfigQceEntry 204 }

gamQosConfigQceLlcControlMask OBJECT-TYPE
    SYNTAX      GAMUnsigned8
    MAX-ACCESS  read-write
    STATUS      current
    DESCRIPTION
        "Indicates the 8 bit LLC Control mask.
         
         Valid values are 0x00 or 0xFF.
         
         This object can only be configured if FrameType is llc(2).
         
         This object is only available if the capability object
         'gamQosCapabilitiesHasQce' is True."
    ::= { gamQosConfigQceEntry 205 }

gamQosConfigQceSnapPid OBJECT-TYPE
    SYNTAX      GAMUnsigned16
    MAX-ACCESS  read-write
    STATUS      current
    DESCRIPTION
        "Indicates the packet's 16 bit SNAP PID field.
         
         The packet's SNAP PID field is AND-ed with the value of SnapPidMask and
         then compared against the value of this object.
         
         If this object value and the value of SnapPidMask is 0x0000, this entry
         matches any ethertype.
         
         This object can only be configured if FrameType is snap(3).
         
         This object is only available if the capability object
         'gamQosCapabilitiesHasQce' is True."
    ::= { gamQosConfigQceEntry 302 }

gamQosConfigQceSnapPidMask OBJECT-TYPE
    SYNTAX      GAMUnsigned16
    MAX-ACCESS  read-write
    STATUS      current
    DESCRIPTION
        "Indicates the 16 bit SNAP PID mask.
         
         Valid values are 0x0000 or 0xFFFF.
         
         This object can only be configured if FrameType is snap(3).
         
         This object is only available if the capability object
         'gamQosCapabilitiesHasQce' is True."
    ::= { gamQosConfigQceEntry 303 }

gamQosConfigQceIpv4Fragment OBJECT-TYPE
    SYNTAX      GAMBitType
    MAX-ACCESS  read-write
    STATUS      current
    DESCRIPTION
        "Indicates how an IPv4 fragment bit is to be compared.
         
         This object can only be configured if FrameType is ipv4(4).
         
         This object is only available if the capability object
         'gamQosCapabilitiesHasQce' is True."
    ::= { gamQosConfigQceEntry 400 }

gamQosConfigQceIpv4DscpOp OBJECT-TYPE
    SYNTAX      GAMASRType
    MAX-ACCESS  read-write
    STATUS      current
    DESCRIPTION
        "Indicates how an IPv4 DSCP field is to be compared.
         
         This object can only be configured if FrameType is ipv4(4).
         
         This object is only available if the capability object
         'gamQosCapabilitiesHasQce' is True."
    ::= { gamQosConfigQceEntry 401 }

gamQosConfigQceIpv4Dscp OBJECT-TYPE
    SYNTAX      Dscp
    MAX-ACCESS  read-write
    STATUS      current
    DESCRIPTION
        "The DSCP value to be compared.
         
         If the Ipv4DscpOp object in the same row is range(2), this object will
         be the starting DSCP value of the range.
         
         Valid range is 0-63.
         
         This object can only be configured if FrameType is ipv4(4) and
         Ipv4DscpOp is not any(0).
         
         This object is only available if the capability object
         'gamQosCapabilitiesHasQce' is True."
    ::= { gamQosConfigQceEntry 402 }

gamQosConfigQceIpv4DscpRange OBJECT-TYPE
    SYNTAX      Dscp
    MAX-ACCESS  read-write
    STATUS      current
    DESCRIPTION
        "The DSCP value to be compared.
         
         If the Ipv4DscpOp object in the same row is range(2), this object will
         be the ending DSCP value of the range.
         
         Valid range is 0-63.
         
         This object can only be configured if FrameType is ipv4(4) and
         Ipv4DscpOp is range(2).
         
         This object is only available if the capability object
         'gamQosCapabilitiesHasQce' is True."
    ::= { gamQosConfigQceEntry 403 }

gamQosConfigQceIpv4Protocol OBJECT-TYPE
    SYNTAX      GAMUnsigned8
    MAX-ACCESS  read-write
    STATUS      current
    DESCRIPTION
        "The protocol number field in the IPv4 header used to indicate a higher
         layer protocol.
         
         The packet's protocol number field is AND-ed with the value of
         Ipv4ProtocolMask and then compared with the value of this object.
         
         If Ipv4Protocol and Ipv4protocolMask are 0, this entry matches any IPv4
         protocol.
         
         Valid range is 0-255.
         
         This object can only be configured if FrameType is ipv4(4).
         
         This object is only available if the capability object
         'gamQosCapabilitiesHasQce' is True."
    ::= { gamQosConfigQceEntry 404 }

gamQosConfigQceIpv4ProtocolMask OBJECT-TYPE
    SYNTAX      GAMUnsigned8
    MAX-ACCESS  read-write
    STATUS      current
    DESCRIPTION
        "The specified IPv4 protocol number mask.
         
         Valid values are 0 or 255.
         
         This object can only be configured if FrameType is ipv4(4).
         
         This object is only available if the capability object
         'gamQosCapabilitiesHasQce' is True."
    ::= { gamQosConfigQceEntry 405 }

gamQosConfigQceIpv4SrcIp OBJECT-TYPE
    SYNTAX      IpAddress
    MAX-ACCESS  read-write
    STATUS      current
    DESCRIPTION
        "The specified IPv4 source address.
         
         The packet's source address is AND-ed with the value of Ipv4SrcIpMask
         and then compared with the value of this object.
         
         If Ipv4SrcIP and Ipv4SrcIpMask are 0.0.0.0, this entry matches any IPv4
         source address.
         
         This object can only be configured if FrameType is ipv4(4).
         
         This object is only available if the capability object
         'gamQosCapabilitiesHasQce' is True."
    ::= { gamQosConfigQceEntry 406 }

gamQosConfigQceIpv4SrcIpMask OBJECT-TYPE
    SYNTAX      IpAddress
    MAX-ACCESS  read-write
    STATUS      current
    DESCRIPTION
        "The specified IPv4 source address mask.
         
         This object can only be configured if FrameType is ipv4(4).
         
         This object is only available if the capability object
         'gamQosCapabilitiesHasQce' is True."
    ::= { gamQosConfigQceEntry 407 }

gamQosConfigQceIpv4DestIp OBJECT-TYPE
    SYNTAX      IpAddress
    MAX-ACCESS  read-write
    STATUS      current
    DESCRIPTION
        "The specified IPv4 destination address.
         
         The packet's destination address is AND-ed with the value of
         Ipv4DestIpMask and then compared with the value of this object.
         
         If Ipv4DestIP and Ipv4DestIpMask are 0.0.0.0, this entry matches any
         IPv4 destination address.
         
         This object can only be configured if FrameType is ipv4(4).
         
         
         
         This object is only available if the capability object
         'gamQosCapabilitiesHasQceDip' is True."
    ::= { gamQosConfigQceEntry 408 }

gamQosConfigQceIpv4DestIpMask OBJECT-TYPE
    SYNTAX      IpAddress
    MAX-ACCESS  read-write
    STATUS      current
    DESCRIPTION
        "The specified IPv4 destination address mask.
         
         This object can only be configured if FrameType is ipv4(4).
         
         
         
         This object is only available if the capability object
         'gamQosCapabilitiesHasQceDip' is True."
    ::= { gamQosConfigQceEntry 409 }

gamQosConfigQceIpv4SrcPortOp OBJECT-TYPE
    SYNTAX      GAMASRType
    MAX-ACCESS  read-write
    STATUS      current
    DESCRIPTION
        "Indicates how a packet's source TCP/UDP port number is to be compared.
         
         This object can only be configured if FrameType is ipv4(4).
         
         This object is only available if the capability object
         'gamQosCapabilitiesHasQce' is True."
    ::= { gamQosConfigQceEntry 410 }

gamQosConfigQceIpv4SrcPort OBJECT-TYPE
    SYNTAX      GAMUnsigned16
    MAX-ACCESS  read-write
    STATUS      current
    DESCRIPTION
        "The source port number of the TCP or UDP protocol.
         
         If the Ipv4SrcPortOp object in the same row is range(2), this object
         will be the starting port number of the port range.
         
         Valid range is 0-65535.
         
         This object can only be configured if FrameType is ipv4(4) and
         Ipv4SrcPortOp is not any(0).
         
         This object is only available if the capability object
         'gamQosCapabilitiesHasQce' is True."
    ::= { gamQosConfigQceEntry 411 }

gamQosConfigQceIpv4SrcPortRange OBJECT-TYPE
    SYNTAX      GAMUnsigned16
    MAX-ACCESS  read-write
    STATUS      current
    DESCRIPTION
        "The source port number of the TCP or UDP protocol.
         
         If the Ipv4SrcPortOp object in the same row is range(2), this object
         will be the ending port number of the port range.
         
         Valid range is 0-65535.
         
         This object can only be configured if FrameType is ipv4(4) and
         Ipv4SrcPortOp is range(2).
         
         This object is only available if the capability object
         'gamQosCapabilitiesHasQce' is True."
    ::= { gamQosConfigQceEntry 412 }

gamQosConfigQceIpv4DestPortOp OBJECT-TYPE
    SYNTAX      GAMASRType
    MAX-ACCESS  read-write
    STATUS      current
    DESCRIPTION
        "Indicates how a packet's destination TCP/UDP port number is to be
         compared.
         
         This object can only be configured if FrameType is ipv4(4).
         
         This object is only available if the capability object
         'gamQosCapabilitiesHasQce' is True."
    ::= { gamQosConfigQceEntry 413 }

gamQosConfigQceIpv4DestPort OBJECT-TYPE
    SYNTAX      GAMUnsigned16
    MAX-ACCESS  read-write
    STATUS      current
    DESCRIPTION
        "The destination port number of the TCP or UDP protocol.
         
         If the Ipv4DestPortOp object in the same row is range(2), this object
         will be the starting port number of the port range.
         
         Valid range is 0-65535.
         
         This object can only be configured if FrameType is ipv4(4) and
         Ipv4DestPortOp is not any(0).
         
         This object is only available if the capability object
         'gamQosCapabilitiesHasQce' is True."
    ::= { gamQosConfigQceEntry 414 }

gamQosConfigQceIpv4DestPortRange OBJECT-TYPE
    SYNTAX      GAMUnsigned16
    MAX-ACCESS  read-write
    STATUS      current
    DESCRIPTION
        "The source port number of the TCP or UDP protocol.
         
         If the Ipv4DestPortOp object in the same row is range(2), this object
         will be the ending port number of the port range.
         
         Valid range is 0-65535.
         
         This object can only be configured if FrameType is ipv4(4) and
         Ipv4DestPortOp is range(2).
         
         This object is only available if the capability object
         'gamQosCapabilitiesHasQce' is True."
    ::= { gamQosConfigQceEntry 415 }

gamQosConfigQceIpv6DscpOp OBJECT-TYPE
    SYNTAX      GAMASRType
    MAX-ACCESS  read-write
    STATUS      current
    DESCRIPTION
        "Indicates how an IPv6 DSCP field is to be compared.
         
         This object can only be configured if FrameType is ipv6(5).
         
         This object is only available if the capability object
         'gamQosCapabilitiesHasQce' is True."
    ::= { gamQosConfigQceEntry 500 }

gamQosConfigQceIpv6Dscp OBJECT-TYPE
    SYNTAX      Dscp
    MAX-ACCESS  read-write
    STATUS      current
    DESCRIPTION
        "The DSCP value to be compared.
         
         If the Ipv6DscpOp object in the same row is range(2), this object will
         be the starting DSCP value of the range.
         
         Valid range is 0-63.
         
         This object can only be configured if FrameType is ipv6(5) and
         Ipv6DscpOp is not any(0).
         
         This object is only available if the capability object
         'gamQosCapabilitiesHasQce' is True."
    ::= { gamQosConfigQceEntry 501 }

gamQosConfigQceIpv6DscpRange OBJECT-TYPE
    SYNTAX      Dscp
    MAX-ACCESS  read-write
    STATUS      current
    DESCRIPTION
        "The DSCP value to be compared.
         
         If the Ipv6DscpOp object in the same row is range(2), this object will
         be the ending DSCP value of the range.
         
         Valid range is 0-63.
         
         This object can only be configured if FrameType is ipv6(5) and
         Ipv6DscpOp is range(2).
         
         This object is only available if the capability object
         'gamQosCapabilitiesHasQce' is True."
    ::= { gamQosConfigQceEntry 502 }

gamQosConfigQceIpv6Protocol OBJECT-TYPE
    SYNTAX      GAMUnsigned8
    MAX-ACCESS  read-write
    STATUS      current
    DESCRIPTION
        "The protocol number field in the IPv6 header used to indicate a higher
         layer protocol.
         
         The packet's protocol number field is AND-ed with the value of
         Ipv6ProtocolMask and then compared with the value of this object.
         
         If Ipv46rotocol and Ipv6protocolMask are 0, this entry matches any IPv6
         protocol.
         
         Valid range is 0-255.
         
         This object can only be configured if FrameType is ipv6(5).
         
         This object is only available if the capability object
         'gamQosCapabilitiesHasQce' is True."
    ::= { gamQosConfigQceEntry 503 }

gamQosConfigQceIpv6ProtocolMask OBJECT-TYPE
    SYNTAX      GAMUnsigned8
    MAX-ACCESS  read-write
    STATUS      current
    DESCRIPTION
        "The specified IPv6 protocol number mask.
         
         Valid values are 0 or 255.
         
         This object can only be configured if FrameType is ipv6(5).
         
         This object is only available if the capability object
         'gamQosCapabilitiesHasQce' is True."
    ::= { gamQosConfigQceEntry 504 }

gamQosConfigQceIpv6SrcIp OBJECT-TYPE
    SYNTAX      InetAddressIPv6
    MAX-ACCESS  read-write
    STATUS      current
    DESCRIPTION
        "The specified IPv6 source address.
         
         The packet's source address is AND-ed with the value of Ipv6SrcIpMask
         and then compared with the value of this object.
         
         If Ipv6SrcIP and Ipv6SrcIpMask are all zeros, this entry matches any
         IPv6 source address.
         
         Only the least significant 32 bits of this object are used.
         
         This object can only be configured if FrameType is ipv6(5).
         
         This object is only available if the capability object
         'gamQosCapabilitiesHasQce' is True."
    ::= { gamQosConfigQceEntry 506 }

gamQosConfigQceIpv6SrcIpMask OBJECT-TYPE
    SYNTAX      InetAddressIPv6
    MAX-ACCESS  read-write
    STATUS      current
    DESCRIPTION
        "The specified IPv6 source address mask.
         
         Only the least significant 32 bits of this object are used.
         
         This object can only be configured if FrameType is ipv6(5).
         
         This object is only available if the capability object
         'gamQosCapabilitiesHasQce' is True."
    ::= { gamQosConfigQceEntry 508 }

gamQosConfigQceIpv6DestIp OBJECT-TYPE
    SYNTAX      InetAddressIPv6
    MAX-ACCESS  read-write
    STATUS      current
    DESCRIPTION
        "The specified IPv6 destination address.
         
         The packet's destination address is AND-ed with the value of
         Ipv6DestIpMask and then compared with the value of this object.
         
         If Ipv6DestIP and Ipv6DestIpMask are all zeros, this entry matches any
         IPv6 destination address.
         
         Only the least significant 32 bits of this object are used.
         
         This object can only be configured if FrameType is ipv6(5).
         
         
         
         This object is only available if the capability object
         'gamQosCapabilitiesHasQceDip' is True."
    ::= { gamQosConfigQceEntry 510 }

gamQosConfigQceIpv6DestIpMask OBJECT-TYPE
    SYNTAX      InetAddressIPv6
    MAX-ACCESS  read-write
    STATUS      current
    DESCRIPTION
        "The specified IPv6 destination address mask.
         
         Only the least significant 32 bits of this object are used.
         
         This object can only be configured if FrameType is ipv6(5).
         
         
         
         This object is only available if the capability object
         'gamQosCapabilitiesHasQceDip' is True."
    ::= { gamQosConfigQceEntry 512 }

gamQosConfigQceIpv6SrcPortOp OBJECT-TYPE
    SYNTAX      GAMASRType
    MAX-ACCESS  read-write
    STATUS      current
    DESCRIPTION
        "Indicates how a packet's source TCP/UDP port number is to be compared.
         
         This object can only be configured if FrameType is ipv6(5).
         
         This object is only available if the capability object
         'gamQosCapabilitiesHasQce' is True."
    ::= { gamQosConfigQceEntry 513 }

gamQosConfigQceIpv6SrcPort OBJECT-TYPE
    SYNTAX      GAMUnsigned16
    MAX-ACCESS  read-write
    STATUS      current
    DESCRIPTION
        "The source port number of the TCP or UDP protocol.
         
         If the Ipv6SrcPortOp object in the same row is range(2), this object
         will be the starting port number of the port range.
         
         Valid range is 0-65535.
         
         This object can only be configured if FrameType is ipv6(5) and
         Ipv6SrcPortOp is not any(0).
         
         This object is only available if the capability object
         'gamQosCapabilitiesHasQce' is True."
    ::= { gamQosConfigQceEntry 514 }

gamQosConfigQceIpv6SrcPortRange OBJECT-TYPE
    SYNTAX      GAMUnsigned16
    MAX-ACCESS  read-write
    STATUS      current
    DESCRIPTION
        "The source port number of the TCP or UDP protocol.
         
         If the Ipv6SrcPortOp object in the same row is range(2), this object
         will be the ending port number of the port range.
         
         Valid range is 0-65535.
         
         This object can only be configured if FrameType is ipv6(5) and
         Ipv6SrcPortOp is range(2).
         
         This object is only available if the capability object
         'gamQosCapabilitiesHasQce' is True."
    ::= { gamQosConfigQceEntry 515 }

gamQosConfigQceIpv6DestPortOp OBJECT-TYPE
    SYNTAX      GAMASRType
    MAX-ACCESS  read-write
    STATUS      current
    DESCRIPTION
        "Indicates how a packet's destination TCP/UDP port number is to be
         compared.
         
         This object can only be configured if FrameType is ipv6(5).
         
         This object is only available if the capability object
         'gamQosCapabilitiesHasQce' is True."
    ::= { gamQosConfigQceEntry 516 }

gamQosConfigQceIpv6DestPort OBJECT-TYPE
    SYNTAX      GAMUnsigned16
    MAX-ACCESS  read-write
    STATUS      current
    DESCRIPTION
        "The destination port number of the TCP or UDP protocol.
         
         If the Ipv6DestPortOp object in the same row is range(2), this object
         will be the starting port number of the port range.
         
         Valid range is 0-65535.
         
         This object can only be configured if FrameType is ipv6(5) and
         Ipv6DestPortOp is not any(0).
         
         This object is only available if the capability object
         'gamQosCapabilitiesHasQce' is True."
    ::= { gamQosConfigQceEntry 517 }

gamQosConfigQceIpv6DestPortRange OBJECT-TYPE
    SYNTAX      GAMUnsigned16
    MAX-ACCESS  read-write
    STATUS      current
    DESCRIPTION
        "The source port number of the TCP or UDP protocol.
         
         If the Ipv6DestPortOp object in the same row is range(2), this object
         will be the ending port number of the port range.
         
         Valid range is 0-65535.
         
         This object can only be configured if FrameType is ipv6(5) and
         Ipv6DestPortOp is range(2).
         
         This object is only available if the capability object
         'gamQosCapabilitiesHasQce' is True."
    ::= { gamQosConfigQceEntry 518 }

gamQosConfigQceActionCosEnable OBJECT-TYPE
    SYNTAX      TruthValue
    MAX-ACCESS  read-write
    STATUS      current
    DESCRIPTION
        "If true, the packet is classified to the CoS value in ActionCos.
         
         This object is only available if the capability object
         'gamQosCapabilitiesHasQce' is True."
    ::= { gamQosConfigQceEntry 1000 }

gamQosConfigQceActionCos OBJECT-TYPE
    SYNTAX      Unsigned32
    MAX-ACCESS  read-write
    STATUS      current
    DESCRIPTION
        "The CoS value used for classification.
         
         Valid range is qosCapabilitiesClassMin-qosCapabilitiesClassMax.
         
         This object is only available if the capability object
         'gamQosCapabilitiesHasQce' is True."
    ::= { gamQosConfigQceEntry 1001 }

gamQosConfigQceActionDplEnable OBJECT-TYPE
    SYNTAX      TruthValue
    MAX-ACCESS  read-write
    STATUS      current
    DESCRIPTION
        "If true, the packet is classified to the DPL value in ActionDpl.
         
         This object is only available if the capability object
         'gamQosCapabilitiesHasQce' is True."
    ::= { gamQosConfigQceEntry 1002 }

gamQosConfigQceActionDpl OBJECT-TYPE
    SYNTAX      GAMUnsigned8
    MAX-ACCESS  read-write
    STATUS      current
    DESCRIPTION
        "The DPL value used for classification.
         
         Valid range is qosCapabilitiesDplMin-qosCapabilitiesDplMax.
         
         This object is only available if the capability object
         'gamQosCapabilitiesHasQce' is True."
    ::= { gamQosConfigQceEntry 1003 }

gamQosConfigQceActionDscpEnable OBJECT-TYPE
    SYNTAX      TruthValue
    MAX-ACCESS  read-write
    STATUS      current
    DESCRIPTION
        "If true, the packet is classified to the DSCP value in ActionDscp.
         
         This object is only available if the capability object
         'gamQosCapabilitiesHasQce' is True."
    ::= { gamQosConfigQceEntry 1004 }

gamQosConfigQceActionDscp OBJECT-TYPE
    SYNTAX      GAMUnsigned8
    MAX-ACCESS  read-write
    STATUS      current
    DESCRIPTION
        "The DSCP value used for classification.
         
         Valid range is 0-63.
         
         This object is only available if the capability object
         'gamQosCapabilitiesHasQce' is True."
    ::= { gamQosConfigQceEntry 1005 }

gamQosConfigQceActionPcpDeiEnable OBJECT-TYPE
    SYNTAX      TruthValue
    MAX-ACCESS  read-write
    STATUS      current
    DESCRIPTION
        "If true, the packet is classified to the PCP value in ActionPcp and the
         DEI value in ActionDei.
         
         
         
         This object is only available if the capability object
         'gamQosCapabilitiesHasQceActionPcpDei' is True."
    ::= { gamQosConfigQceEntry 1006 }

gamQosConfigQceActionPcp OBJECT-TYPE
    SYNTAX      Unsigned32
    MAX-ACCESS  read-write
    STATUS      current
    DESCRIPTION
        "The PCP value used for classification.
         
         Valid range is 0-7.
         
         
         
         This object is only available if the capability object
         'gamQosCapabilitiesHasQceActionPcpDei' is True."
    ::= { gamQosConfigQceEntry 1007 }

gamQosConfigQceActionDei OBJECT-TYPE
    SYNTAX      GAMUnsigned8
    MAX-ACCESS  read-write
    STATUS      current
    DESCRIPTION
        "The DEI value used for classification.
         
         Valid range is 0-1.
         
         
         
         This object is only available if the capability object
         'gamQosCapabilitiesHasQceActionPcpDei' is True."
    ::= { gamQosConfigQceEntry 1008 }

gamQosConfigQceActionPolicyEnable OBJECT-TYPE
    SYNTAX      TruthValue
    MAX-ACCESS  read-write
    STATUS      current
    DESCRIPTION
        "If true, the packet is classified to the policy number in ActionPolicy.
         
         
         
         This object is only available if the capability object
         'gamQosCapabilitiesHasQceActionPolicy' is True."
    ::= { gamQosConfigQceEntry 1009 }

gamQosConfigQceActionPolicy OBJECT-TYPE
    SYNTAX      Unsigned32
    MAX-ACCESS  read-write
    STATUS      current
    DESCRIPTION
        "The policy number used for classification.
         
         Valid range is documented in the ACL MIB.
         
         
         
         This object is only available if the capability object
         'gamQosCapabilitiesHasQceActionPolicy' is True."
    ::= { gamQosConfigQceEntry 1010 }

gamQosConfigQceActionMapEnable OBJECT-TYPE
    SYNTAX      TruthValue
    MAX-ACCESS  read-write
    STATUS      current
    DESCRIPTION
        "If true, the packet is classified by the Ingress Map Id in ActionMap.
         
         
         
         This object is only available if the capability object
         'gamQosCapabilitiesHasQceActionMap' is True."
    ::= { gamQosConfigQceEntry 1011 }

gamQosConfigQceActionMap OBJECT-TYPE
    SYNTAX      GAMUnsigned16
    MAX-ACCESS  read-write
    STATUS      current
    DESCRIPTION
        "The Id of an Ingress Map used for classification.
         
         Valid range is
         qosCapabilitiesIngressMapIdMin-qosCapabilitiesIngressMapIdMax.
         
         
         
         This object is only available if the capability object
         'gamQosCapabilitiesHasQceActionMap' is True."
    ::= { gamQosConfigQceEntry 1012 }

gamQosConfigQceAction OBJECT-TYPE
    SYNTAX      GAMRowEditorState
    MAX-ACCESS  read-write
    STATUS      current
    DESCRIPTION
        "Action
         
         This object is only available if the capability object
         'gamQosCapabilitiesHasQce' is True."
    ::= { gamQosConfigQceEntry 10000 }

gamQosConfigQceTableRowEditor OBJECT IDENTIFIER
    ::= { gamQosConfigQce 2 }

gamQosConfigQceTableRowEditorQceId OBJECT-TYPE
    SYNTAX      Integer32 (0..2147483647)
    MAX-ACCESS  read-write
    STATUS      current
    DESCRIPTION
        "QCE Id.
         
         Valid range is qosCapabilitiesQceIdMin-qosCapabilitiesQceIdMax or 0.
         
         Using a value of 0 when adding a new QCE, will assign the QCE Id in the
         new QCE to the first unused QCE Id.
         
         This object is only available if the capability object
         'gamQosCapabilitiesHasQce' is True."
    ::= { gamQosConfigQceTableRowEditor 1 }

gamQosConfigQceTableRowEditorNextQceId OBJECT-TYPE
    SYNTAX      Unsigned32
    MAX-ACCESS  read-write
    STATUS      current
    DESCRIPTION
        "QCE Id of the next QCE. Valid range is
         qosCapabilitiesQceIdMin-qosCapabilitiesQceIdMax or 0.
         
         The value 0, denotes the end of the list.
         
         This object is only available if the capability object
         'gamQosCapabilitiesHasQce' is True."
    ::= { gamQosConfigQceTableRowEditor 2 }

gamQosConfigQceTableRowEditorSwitchId OBJECT-TYPE
    SYNTAX      Unsigned32
    MAX-ACCESS  read-write
    STATUS      current
    DESCRIPTION
        "Indicates the switch on which this QCE is active.Valid range is
         documented in the Stacking MIB.
         
         This object is only valid on stacking platforms.
         
         This object is only available if the capability object
         'gamQosCapabilitiesHasQce' is True."
    ::= { gamQosConfigQceTableRowEditor 3 }

gamQosConfigQceTableRowEditorPortList OBJECT-TYPE
    SYNTAX      GAMPortList
    MAX-ACCESS  read-write
    STATUS      current
    DESCRIPTION
        "List of ports that are member of this QCE.
         
         This object is only available if the capability object
         'gamQosCapabilitiesHasQce' is True."
    ::= { gamQosConfigQceTableRowEditor 4 }

gamQosConfigQceTableRowEditorDestMacType OBJECT-TYPE
    SYNTAX      GAMDestMacType
    MAX-ACCESS  read-write
    STATUS      current
    DESCRIPTION
        "Indicates the destination MAC type to match.
         
         This object is only available if the capability object
         'gamQosCapabilitiesHasQce' is True."
    ::= { gamQosConfigQceTableRowEditor 5 }

gamQosConfigQceTableRowEditorDestMac OBJECT-TYPE
    SYNTAX      MacAddress
    MAX-ACCESS  read-write
    STATUS      current
    DESCRIPTION
        "Indicates the 48 bits destination MAC address.
         
         The packet's destination address is AND-ed with the value of
         DestMacMask and then compared against the value of this object.
         
         If this object value and the value of DestMacMask is 00-00-00-00-00-00,
         this entry matches any destination MAC address.
         
         This object can only be configured if DestMacType is any(0) and
         DestMacMask is ff-ff-ff-ff-ff-ff.
         
         
         
         This object is only available if the capability object
         'gamQosCapabilitiesHasQceDmac' is True."
    ::= { gamQosConfigQceTableRowEditor 6 }

gamQosConfigQceTableRowEditorDestMacMask OBJECT-TYPE
    SYNTAX      MacAddress
    MAX-ACCESS  read-write
    STATUS      current
    DESCRIPTION
        "Indicates the 48 bits destination MAC address mask.
         
         Valid values are 00-00-00-00-00-00 or ff-ff-ff-ff-ff-ff.
         
         
         
         This object is only available if the capability object
         'gamQosCapabilitiesHasQceDmac' is True."
    ::= { gamQosConfigQceTableRowEditor 7 }

gamQosConfigQceTableRowEditorSrcMac OBJECT-TYPE
    SYNTAX      MacAddress
    MAX-ACCESS  read-write
    STATUS      current
    DESCRIPTION
        "Indicates the 48 bits source MAC address.
         
         The packet's source address is AND-ed with the value of SrcMacMask and
         then compared against the value of this object.
         
         If this object value and the value of SrcMacMask is 00-00-00-00-00-00,
         this entry matches any source MAC address.
         
         This object can only be configured if SrcMacMask is ff-ff-ff-ff-ff-ff.
         
         If the value of qosCapabilitiesHasQceMacOui is true then only the OUI
         part of the MAC address (24 most significant bits) is used.
         
         This object is only available if the capability object
         'gamQosCapabilitiesHasQce' is True."
    ::= { gamQosConfigQceTableRowEditor 8 }

gamQosConfigQceTableRowEditorSrcMacMask OBJECT-TYPE
    SYNTAX      MacAddress
    MAX-ACCESS  read-write
    STATUS      current
    DESCRIPTION
        "Indicates the 48 bits source MAC address mask.
         
         Valid values are 00-00-00-00-00-00 or ff-ff-ff-ff-ff-ff.
         
         This object is only available if the capability object
         'gamQosCapabilitiesHasQce' is True."
    ::= { gamQosConfigQceTableRowEditor 9 }

gamQosConfigQceTableRowEditorVlanTagType OBJECT-TYPE
    SYNTAX      GAMVlanTagType
    MAX-ACCESS  read-write
    STATUS      current
    DESCRIPTION
        "Indicates the VLAN tag type to match.
         
         The value cTagged(3) is only supported if qosCapabilitiesHasQceCTag is
         true.
         
         The value sTagged(3) is only supported if qosCapabilitiesHasQceSTag is
         true.
         
         This object is only available if the capability object
         'gamQosCapabilitiesHasQce' is True."
    ::= { gamQosConfigQceTableRowEditor 10 }

gamQosConfigQceTableRowEditorVlanIdOp OBJECT-TYPE
    SYNTAX      GAMASRType
    MAX-ACCESS  read-write
    STATUS      current
    DESCRIPTION
        "Indicates how a packets's VLAN ID is to be compared.
         
         This object is only available if the capability object
         'gamQosCapabilitiesHasQce' is True."
    ::= { gamQosConfigQceTableRowEditor 11 }

gamQosConfigQceTableRowEditorVlanId OBJECT-TYPE
    SYNTAX      GAMUnsigned16
    MAX-ACCESS  read-write
    STATUS      current
    DESCRIPTION
        "The VLAN ID to be compared.
         
         If the VlanIdOp object in the same row is range(2), this object will be
         the starting VLAN ID of the range.
         
         Valid range is 0-4095.
         
         This object can only be configured if VlanIdOp is not any(0).
         
         This object is only available if the capability object
         'gamQosCapabilitiesHasQce' is True."
    ::= { gamQosConfigQceTableRowEditor 12 }

gamQosConfigQceTableRowEditorVlanIdRange OBJECT-TYPE
    SYNTAX      GAMUnsigned16
    MAX-ACCESS  read-write
    STATUS      current
    DESCRIPTION
        "The VLAN ID to be compared.
         
         If the VlanIdOp object in the same row is range(2), this object will be
         the ending VLAN ID of the range.
         
         Valid range is 0-4095.
         
         This object can only be configured if VlanIdOp is range(2).
         
         This object is only available if the capability object
         'gamQosCapabilitiesHasQce' is True."
    ::= { gamQosConfigQceTableRowEditor 13 }

gamQosConfigQceTableRowEditorPcp OBJECT-TYPE
    SYNTAX      GAMVlanTagPriority
    MAX-ACCESS  read-write
    STATUS      current
    DESCRIPTION
        "The PCP value(s) to be compared.
         
         This object is only available if the capability object
         'gamQosCapabilitiesHasQce' is True."
    ::= { gamQosConfigQceTableRowEditor 14 }

gamQosConfigQceTableRowEditorDei OBJECT-TYPE
    SYNTAX      GAMBitType
    MAX-ACCESS  read-write
    STATUS      current
    DESCRIPTION
        "The DEI value to be compared.
         
         Valid range is 0-1.
         
         This object is only available if the capability object
         'gamQosCapabilitiesHasQce' is True."
    ::= { gamQosConfigQceTableRowEditor 15 }

gamQosConfigQceTableRowEditorInnerVlanTagType OBJECT-TYPE
    SYNTAX      GAMVlanTagType
    MAX-ACCESS  read-write
    STATUS      current
    DESCRIPTION
        "Indicates the inner VLAN tag type to match.
         
         
         
         This object is only available if the capability object
         'gamQosCapabilitiesHasQceInnerTag' is True."
    ::= { gamQosConfigQceTableRowEditor 16 }

gamQosConfigQceTableRowEditorInnerVlanIdOp OBJECT-TYPE
    SYNTAX      GAMASRType
    MAX-ACCESS  read-write
    STATUS      current
    DESCRIPTION
        "Indicates how a packets's inner VLAN ID is to be compared.
         
         
         
         This object is only available if the capability object
         'gamQosCapabilitiesHasQceInnerTag' is True."
    ::= { gamQosConfigQceTableRowEditor 17 }

gamQosConfigQceTableRowEditorInnerVlanId OBJECT-TYPE
    SYNTAX      GAMUnsigned16
    MAX-ACCESS  read-write
    STATUS      current
    DESCRIPTION
        "The inner VLAN ID to be compared.
         
         If the InnerVlanIdOp object in the same row is range(2), this object
         will be the starting VLAN ID of the range.
         
         Valid range is 0-4095.
         
         This object can only be configured if InnerVlanIdOp is not any(0).
         
         
         
         This object is only available if the capability object
         'gamQosCapabilitiesHasQceInnerTag' is True."
    ::= { gamQosConfigQceTableRowEditor 18 }

gamQosConfigQceTableRowEditorInnerVlanIdRange OBJECT-TYPE
    SYNTAX      GAMUnsigned16
    MAX-ACCESS  read-write
    STATUS      current
    DESCRIPTION
        "The inner VLAN ID to be compared.
         
         If the InnerVlanIdOp object in the same row is range(2), this object
         will be the ending VLAN ID of the range.
         
         Valid range is 0-4095.
         
         This object can only be configured if InnerVlanIdOp is range(2).
         
         
         
         This object is only available if the capability object
         'gamQosCapabilitiesHasQceInnerTag' is True."
    ::= { gamQosConfigQceTableRowEditor 19 }

gamQosConfigQceTableRowEditorInnerPcp OBJECT-TYPE
    SYNTAX      GAMVlanTagPriority
    MAX-ACCESS  read-write
    STATUS      current
    DESCRIPTION
        "The inner PCP value(s) to be compared.
         
         
         
         This object is only available if the capability object
         'gamQosCapabilitiesHasQceInnerTag' is True."
    ::= { gamQosConfigQceTableRowEditor 20 }

gamQosConfigQceTableRowEditorInnerDei OBJECT-TYPE
    SYNTAX      GAMBitType
    MAX-ACCESS  read-write
    STATUS      current
    DESCRIPTION
        "The inner DEI value to be compared.
         
         Valid range is 0-1.
         
         
         
         This object is only available if the capability object
         'gamQosCapabilitiesHasQceInnerTag' is True."
    ::= { gamQosConfigQceTableRowEditor 21 }

gamQosConfigQceTableRowEditorFrameType OBJECT-TYPE
    SYNTAX      GAMQosQceFrameType
    MAX-ACCESS  read-write
    STATUS      current
    DESCRIPTION
        "Indicates the packet's frame type.
         
         Modifying the frame type on an existing QCE will restore the content of
         all frame type dependent configuration to default.
         
         This object is only available if the capability object
         'gamQosCapabilitiesHasQce' is True."
    ::= { gamQosConfigQceTableRowEditor 100 }

gamQosConfigQceTableRowEditorEtype OBJECT-TYPE
    SYNTAX      GAMEtherType
    MAX-ACCESS  read-write
    STATUS      current
    DESCRIPTION
        "Indicates the packet's 16 bit Ethernet type field.
         
         Valid values are: 0(match any), 0x600-0xFFFF but excluding 0x800(IPv4)
         and 0x86DD(IPv6).
         
         This object can only be configured if FrameType is etype(1).
         
         This object is only available if the capability object
         'gamQosCapabilitiesHasQce' is True."
    ::= { gamQosConfigQceTableRowEditor 101 }

gamQosConfigQceTableRowEditorLlcDsap OBJECT-TYPE
    SYNTAX      GAMUnsigned8
    MAX-ACCESS  read-write
    STATUS      current
    DESCRIPTION
        "Indicates the packets's 8 bit LLC DSAP field.
         
         The packet's LLC DSAP field is AND-ed with the value of LlcDsapMask and
         then compared against the value of this object.
         
         If this object value and the value of LlcDsapMask is 0x00, this entry
         matches any LLC DSAP.
         
         Valid range is 0x00-0xFF.
         
         This object can only be configured if FrameType is llc(2).
         
         This object is only available if the capability object
         'gamQosCapabilitiesHasQce' is True."
    ::= { gamQosConfigQceTableRowEditor 200 }

gamQosConfigQceTableRowEditorLlcDsapMask OBJECT-TYPE
    SYNTAX      GAMUnsigned8
    MAX-ACCESS  read-write
    STATUS      current
    DESCRIPTION
        "Indicates the 8 bit LLC DSAP mask.
         
         Valid values are 0x00 or 0xFF.
         
         This object can only be configured if FrameType is llc(2).
         
         This object is only available if the capability object
         'gamQosCapabilitiesHasQce' is True."
    ::= { gamQosConfigQceTableRowEditor 201 }

gamQosConfigQceTableRowEditorLlcSsap OBJECT-TYPE
    SYNTAX      GAMUnsigned8
    MAX-ACCESS  read-write
    STATUS      current
    DESCRIPTION
        "Indicates the packets's 8 bit LLC SSAP field.
         
         The packet's LLC SSAP field is AND-ed with the value of LlcSsapMask and
         then compared against the value of this object.
         
         If this object value and the value of LlcSsapMask is 0x00, this entry
         matches any LLC SSAP.
         
         Valid range is 0x00-0xFF.
         
         This object can only be configured if FrameType is llc(2).
         
         This object is only available if the capability object
         'gamQosCapabilitiesHasQce' is True."
    ::= { gamQosConfigQceTableRowEditor 202 }

gamQosConfigQceTableRowEditorLlcSsapMask OBJECT-TYPE
    SYNTAX      GAMUnsigned8
    MAX-ACCESS  read-write
    STATUS      current
    DESCRIPTION
        "Indicates the 8 bit LLC SSAP mask.
         
         Valid values are 0x00 or 0xFF.
         
         This object can only be configured if FrameType is llc(2).
         
         This object is only available if the capability object
         'gamQosCapabilitiesHasQce' is True."
    ::= { gamQosConfigQceTableRowEditor 203 }

gamQosConfigQceTableRowEditorLlcControl OBJECT-TYPE
    SYNTAX      GAMUnsigned8
    MAX-ACCESS  read-write
    STATUS      current
    DESCRIPTION
        "Indicates the packets's 8 bit LLC Control field.
         
         The packet's LLC Control field is AND-ed with the value of
         LlcControlMask and then compared against the value of this object.
         
         If this object value and the value of LlcControlMask is 0x00, this
         entry matches any LLC Control.
         
         Valid range is 0x00-0xFF.
         
         This object can only be configured if FrameType is llc(2).
         
         This object is only available if the capability object
         'gamQosCapabilitiesHasQce' is True."
    ::= { gamQosConfigQceTableRowEditor 204 }

gamQosConfigQceTableRowEditorLlcControlMask OBJECT-TYPE
    SYNTAX      GAMUnsigned8
    MAX-ACCESS  read-write
    STATUS      current
    DESCRIPTION
        "Indicates the 8 bit LLC Control mask.
         
         Valid values are 0x00 or 0xFF.
         
         This object can only be configured if FrameType is llc(2).
         
         This object is only available if the capability object
         'gamQosCapabilitiesHasQce' is True."
    ::= { gamQosConfigQceTableRowEditor 205 }

gamQosConfigQceTableRowEditorSnapPid OBJECT-TYPE
    SYNTAX      GAMUnsigned16
    MAX-ACCESS  read-write
    STATUS      current
    DESCRIPTION
        "Indicates the packet's 16 bit SNAP PID field.
         
         The packet's SNAP PID field is AND-ed with the value of SnapPidMask and
         then compared against the value of this object.
         
         If this object value and the value of SnapPidMask is 0x0000, this entry
         matches any ethertype.
         
         This object can only be configured if FrameType is snap(3).
         
         This object is only available if the capability object
         'gamQosCapabilitiesHasQce' is True."
    ::= { gamQosConfigQceTableRowEditor 302 }

gamQosConfigQceTableRowEditorSnapPidMask OBJECT-TYPE
    SYNTAX      GAMUnsigned16
    MAX-ACCESS  read-write
    STATUS      current
    DESCRIPTION
        "Indicates the 16 bit SNAP PID mask.
         
         Valid values are 0x0000 or 0xFFFF.
         
         This object can only be configured if FrameType is snap(3).
         
         This object is only available if the capability object
         'gamQosCapabilitiesHasQce' is True."
    ::= { gamQosConfigQceTableRowEditor 303 }

gamQosConfigQceTableRowEditorIpv4Fragment OBJECT-TYPE
    SYNTAX      GAMBitType
    MAX-ACCESS  read-write
    STATUS      current
    DESCRIPTION
        "Indicates how an IPv4 fragment bit is to be compared.
         
         This object can only be configured if FrameType is ipv4(4).
         
         This object is only available if the capability object
         'gamQosCapabilitiesHasQce' is True."
    ::= { gamQosConfigQceTableRowEditor 400 }

gamQosConfigQceTableRowEditorIpv4DscpOp OBJECT-TYPE
    SYNTAX      GAMASRType
    MAX-ACCESS  read-write
    STATUS      current
    DESCRIPTION
        "Indicates how an IPv4 DSCP field is to be compared.
         
         This object can only be configured if FrameType is ipv4(4).
         
         This object is only available if the capability object
         'gamQosCapabilitiesHasQce' is True."
    ::= { gamQosConfigQceTableRowEditor 401 }

gamQosConfigQceTableRowEditorIpv4Dscp OBJECT-TYPE
    SYNTAX      Dscp
    MAX-ACCESS  read-write
    STATUS      current
    DESCRIPTION
        "The DSCP value to be compared.
         
         If the Ipv4DscpOp object in the same row is range(2), this object will
         be the starting DSCP value of the range.
         
         Valid range is 0-63.
         
         This object can only be configured if FrameType is ipv4(4) and
         Ipv4DscpOp is not any(0).
         
         This object is only available if the capability object
         'gamQosCapabilitiesHasQce' is True."
    ::= { gamQosConfigQceTableRowEditor 402 }

gamQosConfigQceTableRowEditorIpv4DscpRange OBJECT-TYPE
    SYNTAX      Dscp
    MAX-ACCESS  read-write
    STATUS      current
    DESCRIPTION
        "The DSCP value to be compared.
         
         If the Ipv4DscpOp object in the same row is range(2), this object will
         be the ending DSCP value of the range.
         
         Valid range is 0-63.
         
         This object can only be configured if FrameType is ipv4(4) and
         Ipv4DscpOp is range(2).
         
         This object is only available if the capability object
         'gamQosCapabilitiesHasQce' is True."
    ::= { gamQosConfigQceTableRowEditor 403 }

gamQosConfigQceTableRowEditorIpv4Protocol OBJECT-TYPE
    SYNTAX      GAMUnsigned8
    MAX-ACCESS  read-write
    STATUS      current
    DESCRIPTION
        "The protocol number field in the IPv4 header used to indicate a higher
         layer protocol.
         
         The packet's protocol number field is AND-ed with the value of
         Ipv4ProtocolMask and then compared with the value of this object.
         
         If Ipv4Protocol and Ipv4protocolMask are 0, this entry matches any IPv4
         protocol.
         
         Valid range is 0-255.
         
         This object can only be configured if FrameType is ipv4(4).
         
         This object is only available if the capability object
         'gamQosCapabilitiesHasQce' is True."
    ::= { gamQosConfigQceTableRowEditor 404 }

gamQosConfigQceTableRowEditorIpv4ProtocolMask OBJECT-TYPE
    SYNTAX      GAMUnsigned8
    MAX-ACCESS  read-write
    STATUS      current
    DESCRIPTION
        "The specified IPv4 protocol number mask.
         
         Valid values are 0 or 255.
         
         This object can only be configured if FrameType is ipv4(4).
         
         This object is only available if the capability object
         'gamQosCapabilitiesHasQce' is True."
    ::= { gamQosConfigQceTableRowEditor 405 }

gamQosConfigQceTableRowEditorIpv4SrcIp OBJECT-TYPE
    SYNTAX      IpAddress
    MAX-ACCESS  read-write
    STATUS      current
    DESCRIPTION
        "The specified IPv4 source address.
         
         The packet's source address is AND-ed with the value of Ipv4SrcIpMask
         and then compared with the value of this object.
         
         If Ipv4SrcIP and Ipv4SrcIpMask are 0.0.0.0, this entry matches any IPv4
         source address.
         
         This object can only be configured if FrameType is ipv4(4).
         
         This object is only available if the capability object
         'gamQosCapabilitiesHasQce' is True."
    ::= { gamQosConfigQceTableRowEditor 406 }

gamQosConfigQceTableRowEditorIpv4SrcIpMask OBJECT-TYPE
    SYNTAX      IpAddress
    MAX-ACCESS  read-write
    STATUS      current
    DESCRIPTION
        "The specified IPv4 source address mask.
         
         This object can only be configured if FrameType is ipv4(4).
         
         This object is only available if the capability object
         'gamQosCapabilitiesHasQce' is True."
    ::= { gamQosConfigQceTableRowEditor 407 }

gamQosConfigQceTableRowEditorIpv4DestIp OBJECT-TYPE
    SYNTAX      IpAddress
    MAX-ACCESS  read-write
    STATUS      current
    DESCRIPTION
        "The specified IPv4 destination address.
         
         The packet's destination address is AND-ed with the value of
         Ipv4DestIpMask and then compared with the value of this object.
         
         If Ipv4DestIP and Ipv4DestIpMask are 0.0.0.0, this entry matches any
         IPv4 destination address.
         
         This object can only be configured if FrameType is ipv4(4).
         
         
         
         This object is only available if the capability object
         'gamQosCapabilitiesHasQceDip' is True."
    ::= { gamQosConfigQceTableRowEditor 408 }

gamQosConfigQceTableRowEditorIpv4DestIpMask OBJECT-TYPE
    SYNTAX      IpAddress
    MAX-ACCESS  read-write
    STATUS      current
    DESCRIPTION
        "The specified IPv4 destination address mask.
         
         This object can only be configured if FrameType is ipv4(4).
         
         
         
         This object is only available if the capability object
         'gamQosCapabilitiesHasQceDip' is True."
    ::= { gamQosConfigQceTableRowEditor 409 }

gamQosConfigQceTableRowEditorIpv4SrcPortOp OBJECT-TYPE
    SYNTAX      GAMASRType
    MAX-ACCESS  read-write
    STATUS      current
    DESCRIPTION
        "Indicates how a packet's source TCP/UDP port number is to be compared.
         
         This object can only be configured if FrameType is ipv4(4).
         
         This object is only available if the capability object
         'gamQosCapabilitiesHasQce' is True."
    ::= { gamQosConfigQceTableRowEditor 410 }

gamQosConfigQceTableRowEditorIpv4SrcPort OBJECT-TYPE
    SYNTAX      GAMUnsigned16
    MAX-ACCESS  read-write
    STATUS      current
    DESCRIPTION
        "The source port number of the TCP or UDP protocol.
         
         If the Ipv4SrcPortOp object in the same row is range(2), this object
         will be the starting port number of the port range.
         
         Valid range is 0-65535.
         
         This object can only be configured if FrameType is ipv4(4) and
         Ipv4SrcPortOp is not any(0).
         
         This object is only available if the capability object
         'gamQosCapabilitiesHasQce' is True."
    ::= { gamQosConfigQceTableRowEditor 411 }

gamQosConfigQceTableRowEditorIpv4SrcPortRange OBJECT-TYPE
    SYNTAX      GAMUnsigned16
    MAX-ACCESS  read-write
    STATUS      current
    DESCRIPTION
        "The source port number of the TCP or UDP protocol.
         
         If the Ipv4SrcPortOp object in the same row is range(2), this object
         will be the ending port number of the port range.
         
         Valid range is 0-65535.
         
         This object can only be configured if FrameType is ipv4(4) and
         Ipv4SrcPortOp is range(2).
         
         This object is only available if the capability object
         'gamQosCapabilitiesHasQce' is True."
    ::= { gamQosConfigQceTableRowEditor 412 }

gamQosConfigQceTableRowEditorIpv4DestPortOp OBJECT-TYPE
    SYNTAX      GAMASRType
    MAX-ACCESS  read-write
    STATUS      current
    DESCRIPTION
        "Indicates how a packet's destination TCP/UDP port number is to be
         compared.
         
         This object can only be configured if FrameType is ipv4(4).
         
         This object is only available if the capability object
         'gamQosCapabilitiesHasQce' is True."
    ::= { gamQosConfigQceTableRowEditor 413 }

gamQosConfigQceTableRowEditorIpv4DestPort OBJECT-TYPE
    SYNTAX      GAMUnsigned16
    MAX-ACCESS  read-write
    STATUS      current
    DESCRIPTION
        "The destination port number of the TCP or UDP protocol.
         
         If the Ipv4DestPortOp object in the same row is range(2), this object
         will be the starting port number of the port range.
         
         Valid range is 0-65535.
         
         This object can only be configured if FrameType is ipv4(4) and
         Ipv4DestPortOp is not any(0).
         
         This object is only available if the capability object
         'gamQosCapabilitiesHasQce' is True."
    ::= { gamQosConfigQceTableRowEditor 414 }

gamQosConfigQceTableRowEditorIpv4DestPortRange OBJECT-TYPE
    SYNTAX      GAMUnsigned16
    MAX-ACCESS  read-write
    STATUS      current
    DESCRIPTION
        "The source port number of the TCP or UDP protocol.
         
         If the Ipv4DestPortOp object in the same row is range(2), this object
         will be the ending port number of the port range.
         
         Valid range is 0-65535.
         
         This object can only be configured if FrameType is ipv4(4) and
         Ipv4DestPortOp is range(2).
         
         This object is only available if the capability object
         'gamQosCapabilitiesHasQce' is True."
    ::= { gamQosConfigQceTableRowEditor 415 }

gamQosConfigQceTableRowEditorIpv6DscpOp OBJECT-TYPE
    SYNTAX      GAMASRType
    MAX-ACCESS  read-write
    STATUS      current
    DESCRIPTION
        "Indicates how an IPv6 DSCP field is to be compared.
         
         This object can only be configured if FrameType is ipv6(5).
         
         This object is only available if the capability object
         'gamQosCapabilitiesHasQce' is True."
    ::= { gamQosConfigQceTableRowEditor 500 }

gamQosConfigQceTableRowEditorIpv6Dscp OBJECT-TYPE
    SYNTAX      Dscp
    MAX-ACCESS  read-write
    STATUS      current
    DESCRIPTION
        "The DSCP value to be compared.
         
         If the Ipv6DscpOp object in the same row is range(2), this object will
         be the starting DSCP value of the range.
         
         Valid range is 0-63.
         
         This object can only be configured if FrameType is ipv6(5) and
         Ipv6DscpOp is not any(0).
         
         This object is only available if the capability object
         'gamQosCapabilitiesHasQce' is True."
    ::= { gamQosConfigQceTableRowEditor 501 }

gamQosConfigQceTableRowEditorIpv6DscpRange OBJECT-TYPE
    SYNTAX      Dscp
    MAX-ACCESS  read-write
    STATUS      current
    DESCRIPTION
        "The DSCP value to be compared.
         
         If the Ipv6DscpOp object in the same row is range(2), this object will
         be the ending DSCP value of the range.
         
         Valid range is 0-63.
         
         This object can only be configured if FrameType is ipv6(5) and
         Ipv6DscpOp is range(2).
         
         This object is only available if the capability object
         'gamQosCapabilitiesHasQce' is True."
    ::= { gamQosConfigQceTableRowEditor 502 }

gamQosConfigQceTableRowEditorIpv6Protocol OBJECT-TYPE
    SYNTAX      GAMUnsigned8
    MAX-ACCESS  read-write
    STATUS      current
    DESCRIPTION
        "The protocol number field in the IPv6 header used to indicate a higher
         layer protocol.
         
         The packet's protocol number field is AND-ed with the value of
         Ipv6ProtocolMask and then compared with the value of this object.
         
         If Ipv46rotocol and Ipv6protocolMask are 0, this entry matches any IPv6
         protocol.
         
         Valid range is 0-255.
         
         This object can only be configured if FrameType is ipv6(5).
         
         This object is only available if the capability object
         'gamQosCapabilitiesHasQce' is True."
    ::= { gamQosConfigQceTableRowEditor 503 }

gamQosConfigQceTableRowEditorIpv6ProtocolMask OBJECT-TYPE
    SYNTAX      GAMUnsigned8
    MAX-ACCESS  read-write
    STATUS      current
    DESCRIPTION
        "The specified IPv6 protocol number mask.
         
         Valid values are 0 or 255.
         
         This object can only be configured if FrameType is ipv6(5).
         
         This object is only available if the capability object
         'gamQosCapabilitiesHasQce' is True."
    ::= { gamQosConfigQceTableRowEditor 504 }

gamQosConfigQceTableRowEditorIpv6SrcIp OBJECT-TYPE
    SYNTAX      InetAddressIPv6
    MAX-ACCESS  read-write
    STATUS      current
    DESCRIPTION
        "The specified IPv6 source address.
         
         The packet's source address is AND-ed with the value of Ipv6SrcIpMask
         and then compared with the value of this object.
         
         If Ipv6SrcIP and Ipv6SrcIpMask are all zeros, this entry matches any
         IPv6 source address.
         
         Only the least significant 32 bits of this object are used.
         
         This object can only be configured if FrameType is ipv6(5).
         
         This object is only available if the capability object
         'gamQosCapabilitiesHasQce' is True."
    ::= { gamQosConfigQceTableRowEditor 506 }

gamQosConfigQceTableRowEditorIpv6SrcIpMask OBJECT-TYPE
    SYNTAX      InetAddressIPv6
    MAX-ACCESS  read-write
    STATUS      current
    DESCRIPTION
        "The specified IPv6 source address mask.
         
         Only the least significant 32 bits of this object are used.
         
         This object can only be configured if FrameType is ipv6(5).
         
         This object is only available if the capability object
         'gamQosCapabilitiesHasQce' is True."
    ::= { gamQosConfigQceTableRowEditor 508 }

gamQosConfigQceTableRowEditorIpv6DestIp OBJECT-TYPE
    SYNTAX      InetAddressIPv6
    MAX-ACCESS  read-write
    STATUS      current
    DESCRIPTION
        "The specified IPv6 destination address.
         
         The packet's destination address is AND-ed with the value of
         Ipv6DestIpMask and then compared with the value of this object.
         
         If Ipv6DestIP and Ipv6DestIpMask are all zeros, this entry matches any
         IPv6 destination address.
         
         Only the least significant 32 bits of this object are used.
         
         This object can only be configured if FrameType is ipv6(5).
         
         
         
         This object is only available if the capability object
         'gamQosCapabilitiesHasQceDip' is True."
    ::= { gamQosConfigQceTableRowEditor 510 }

gamQosConfigQceTableRowEditorIpv6DestIpMask OBJECT-TYPE
    SYNTAX      InetAddressIPv6
    MAX-ACCESS  read-write
    STATUS      current
    DESCRIPTION
        "The specified IPv6 destination address mask.
         
         Only the least significant 32 bits of this object are used.
         
         This object can only be configured if FrameType is ipv6(5).
         
         
         
         This object is only available if the capability object
         'gamQosCapabilitiesHasQceDip' is True."
    ::= { gamQosConfigQceTableRowEditor 512 }

gamQosConfigQceTableRowEditorIpv6SrcPortOp OBJECT-TYPE
    SYNTAX      GAMASRType
    MAX-ACCESS  read-write
    STATUS      current
    DESCRIPTION
        "Indicates how a packet's source TCP/UDP port number is to be compared.
         
         This object can only be configured if FrameType is ipv6(5).
         
         This object is only available if the capability object
         'gamQosCapabilitiesHasQce' is True."
    ::= { gamQosConfigQceTableRowEditor 513 }

gamQosConfigQceTableRowEditorIpv6SrcPort OBJECT-TYPE
    SYNTAX      GAMUnsigned16
    MAX-ACCESS  read-write
    STATUS      current
    DESCRIPTION
        "The source port number of the TCP or UDP protocol.
         
         If the Ipv6SrcPortOp object in the same row is range(2), this object
         will be the starting port number of the port range.
         
         Valid range is 0-65535.
         
         This object can only be configured if FrameType is ipv6(5) and
         Ipv6SrcPortOp is not any(0).
         
         This object is only available if the capability object
         'gamQosCapabilitiesHasQce' is True."
    ::= { gamQosConfigQceTableRowEditor 514 }

gamQosConfigQceTableRowEditorIpv6SrcPortRange OBJECT-TYPE
    SYNTAX      GAMUnsigned16
    MAX-ACCESS  read-write
    STATUS      current
    DESCRIPTION
        "The source port number of the TCP or UDP protocol.
         
         If the Ipv6SrcPortOp object in the same row is range(2), this object
         will be the ending port number of the port range.
         
         Valid range is 0-65535.
         
         This object can only be configured if FrameType is ipv6(5) and
         Ipv6SrcPortOp is range(2).
         
         This object is only available if the capability object
         'gamQosCapabilitiesHasQce' is True."
    ::= { gamQosConfigQceTableRowEditor 515 }

gamQosConfigQceTableRowEditorIpv6DestPortOp OBJECT-TYPE
    SYNTAX      GAMASRType
    MAX-ACCESS  read-write
    STATUS      current
    DESCRIPTION
        "Indicates how a packet's destination TCP/UDP port number is to be
         compared.
         
         This object can only be configured if FrameType is ipv6(5).
         
         This object is only available if the capability object
         'gamQosCapabilitiesHasQce' is True."
    ::= { gamQosConfigQceTableRowEditor 516 }

gamQosConfigQceTableRowEditorIpv6DestPort OBJECT-TYPE
    SYNTAX      GAMUnsigned16
    MAX-ACCESS  read-write
    STATUS      current
    DESCRIPTION
        "The destination port number of the TCP or UDP protocol.
         
         If the Ipv6DestPortOp object in the same row is range(2), this object
         will be the starting port number of the port range.
         
         Valid range is 0-65535.
         
         This object can only be configured if FrameType is ipv6(5) and
         Ipv6DestPortOp is not any(0).
         
         This object is only available if the capability object
         'gamQosCapabilitiesHasQce' is True."
    ::= { gamQosConfigQceTableRowEditor 517 }

gamQosConfigQceTableRowEditorIpv6DestPortRange OBJECT-TYPE
    SYNTAX      GAMUnsigned16
    MAX-ACCESS  read-write
    STATUS      current
    DESCRIPTION
        "The source port number of the TCP or UDP protocol.
         
         If the Ipv6DestPortOp object in the same row is range(2), this object
         will be the ending port number of the port range.
         
         Valid range is 0-65535.
         
         This object can only be configured if FrameType is ipv6(5) and
         Ipv6DestPortOp is range(2).
         
         This object is only available if the capability object
         'gamQosCapabilitiesHasQce' is True."
    ::= { gamQosConfigQceTableRowEditor 518 }

gamQosConfigQceTableRowEditorActionCosEnable OBJECT-TYPE
    SYNTAX      TruthValue
    MAX-ACCESS  read-write
    STATUS      current
    DESCRIPTION
        "If true, the packet is classified to the CoS value in ActionCos.
         
         This object is only available if the capability object
         'gamQosCapabilitiesHasQce' is True."
    ::= { gamQosConfigQceTableRowEditor 1000 }

gamQosConfigQceTableRowEditorActionCos OBJECT-TYPE
    SYNTAX      Unsigned32
    MAX-ACCESS  read-write
    STATUS      current
    DESCRIPTION
        "The CoS value used for classification.
         
         Valid range is qosCapabilitiesClassMin-qosCapabilitiesClassMax.
         
         This object is only available if the capability object
         'gamQosCapabilitiesHasQce' is True."
    ::= { gamQosConfigQceTableRowEditor 1001 }

gamQosConfigQceTableRowEditorActionDplEnable OBJECT-TYPE
    SYNTAX      TruthValue
    MAX-ACCESS  read-write
    STATUS      current
    DESCRIPTION
        "If true, the packet is classified to the DPL value in ActionDpl.
         
         This object is only available if the capability object
         'gamQosCapabilitiesHasQce' is True."
    ::= { gamQosConfigQceTableRowEditor 1002 }

gamQosConfigQceTableRowEditorActionDpl OBJECT-TYPE
    SYNTAX      GAMUnsigned8
    MAX-ACCESS  read-write
    STATUS      current
    DESCRIPTION
        "The DPL value used for classification.
         
         Valid range is qosCapabilitiesDplMin-qosCapabilitiesDplMax.
         
         This object is only available if the capability object
         'gamQosCapabilitiesHasQce' is True."
    ::= { gamQosConfigQceTableRowEditor 1003 }

gamQosConfigQceTableRowEditorActionDscpEnable OBJECT-TYPE
    SYNTAX      TruthValue
    MAX-ACCESS  read-write
    STATUS      current
    DESCRIPTION
        "If true, the packet is classified to the DSCP value in ActionDscp.
         
         This object is only available if the capability object
         'gamQosCapabilitiesHasQce' is True."
    ::= { gamQosConfigQceTableRowEditor 1004 }

gamQosConfigQceTableRowEditorActionDscp OBJECT-TYPE
    SYNTAX      GAMUnsigned8
    MAX-ACCESS  read-write
    STATUS      current
    DESCRIPTION
        "The DSCP value used for classification.
         
         Valid range is 0-63.
         
         This object is only available if the capability object
         'gamQosCapabilitiesHasQce' is True."
    ::= { gamQosConfigQceTableRowEditor 1005 }

gamQosConfigQceTableRowEditorActionPcpDeiEnable OBJECT-TYPE
    SYNTAX      TruthValue
    MAX-ACCESS  read-write
    STATUS      current
    DESCRIPTION
        "If true, the packet is classified to the PCP value in ActionPcp and the
         DEI value in ActionDei.
         
         
         
         This object is only available if the capability object
         'gamQosCapabilitiesHasQceActionPcpDei' is True."
    ::= { gamQosConfigQceTableRowEditor 1006 }

gamQosConfigQceTableRowEditorActionPcp OBJECT-TYPE
    SYNTAX      Unsigned32
    MAX-ACCESS  read-write
    STATUS      current
    DESCRIPTION
        "The PCP value used for classification.
         
         Valid range is 0-7.
         
         
         
         This object is only available if the capability object
         'gamQosCapabilitiesHasQceActionPcpDei' is True."
    ::= { gamQosConfigQceTableRowEditor 1007 }

gamQosConfigQceTableRowEditorActionDei OBJECT-TYPE
    SYNTAX      GAMUnsigned8
    MAX-ACCESS  read-write
    STATUS      current
    DESCRIPTION
        "The DEI value used for classification.
         
         Valid range is 0-1.
         
         
         
         This object is only available if the capability object
         'gamQosCapabilitiesHasQceActionPcpDei' is True."
    ::= { gamQosConfigQceTableRowEditor 1008 }

gamQosConfigQceTableRowEditorActionPolicyEnable OBJECT-TYPE
    SYNTAX      TruthValue
    MAX-ACCESS  read-write
    STATUS      current
    DESCRIPTION
        "If true, the packet is classified to the policy number in ActionPolicy.
         
         
         
         This object is only available if the capability object
         'gamQosCapabilitiesHasQceActionPolicy' is True."
    ::= { gamQosConfigQceTableRowEditor 1009 }

gamQosConfigQceTableRowEditorActionPolicy OBJECT-TYPE
    SYNTAX      Unsigned32
    MAX-ACCESS  read-write
    STATUS      current
    DESCRIPTION
        "The policy number used for classification.
         
         Valid range is documented in the ACL MIB.
         
         
         
         This object is only available if the capability object
         'gamQosCapabilitiesHasQceActionPolicy' is True."
    ::= { gamQosConfigQceTableRowEditor 1010 }

gamQosConfigQceTableRowEditorActionMapEnable OBJECT-TYPE
    SYNTAX      TruthValue
    MAX-ACCESS  read-write
    STATUS      current
    DESCRIPTION
        "If true, the packet is classified by the Ingress Map Id in ActionMap.
         
         
         
         This object is only available if the capability object
         'gamQosCapabilitiesHasQceActionMap' is True."
    ::= { gamQosConfigQceTableRowEditor 1011 }

gamQosConfigQceTableRowEditorActionMap OBJECT-TYPE
    SYNTAX      GAMUnsigned16
    MAX-ACCESS  read-write
    STATUS      current
    DESCRIPTION
        "The Id of an Ingress Map used for classification.
         
         Valid range is
         qosCapabilitiesIngressMapIdMin-qosCapabilitiesIngressMapIdMax.
         
         
         
         This object is only available if the capability object
         'gamQosCapabilitiesHasQceActionMap' is True."
    ::= { gamQosConfigQceTableRowEditor 1012 }

gamQosConfigQceTableRowEditorAction OBJECT-TYPE
    SYNTAX      GAMRowEditorState
    MAX-ACCESS  read-write
    STATUS      current
    DESCRIPTION
        "Action
         
         This object is only available if the capability object
         'gamQosCapabilitiesHasQce' is True."
    ::= { gamQosConfigQceTableRowEditor 10000 }

gamQosConfigQcePrecedenceTable OBJECT-TYPE
    SYNTAX      SEQUENCE OF GAMQosConfigQcePrecedenceEntry
    MAX-ACCESS  not-accessible
    STATUS      current
    DESCRIPTION
        "This table contains the precedence of QCEs ordered by their position in
         the QCL.
         
         This is an optional table and is only present if qosCapabilitiesHasQce
         is true."
    ::= { gamQosConfigQce 3 }

gamQosConfigQcePrecedenceEntry OBJECT-TYPE
    SYNTAX      GAMQosConfigQcePrecedenceEntry
    MAX-ACCESS  not-accessible
    STATUS      current
    DESCRIPTION
        "Each row contains the precedence of a single QCE."
    INDEX       { gamQosConfigQcePrecedenceIndex }
    ::= { gamQosConfigQcePrecedenceTable 1 }

GAMQosConfigQcePrecedenceEntry ::= SEQUENCE {
    gamQosConfigQcePrecedenceIndex  Integer32,
    gamQosConfigQcePrecedenceQceId  Unsigned32
}

gamQosConfigQcePrecedenceIndex OBJECT-TYPE
    SYNTAX      Integer32 (0..2147483647)
    MAX-ACCESS  accessible-for-notify
    STATUS      current
    DESCRIPTION
        "QCE precedence index. Indicates the position in QCL.
         
         This object is only available if the capability object
         'gamQosCapabilitiesHasQce' is True."
    ::= { gamQosConfigQcePrecedenceEntry 1 }

gamQosConfigQcePrecedenceQceId OBJECT-TYPE
    SYNTAX      Unsigned32
    MAX-ACCESS  read-only
    STATUS      current
    DESCRIPTION
        "QCE Id.
         
         This object is only available if the capability object
         'gamQosCapabilitiesHasQce' is True."
    ::= { gamQosConfigQcePrecedenceEntry 2 }

gamQosConfigIngressMap OBJECT IDENTIFIER
    ::= { gamQosConfig 4 }

gamQosConfigIngressMapTable OBJECT-TYPE
    SYNTAX      SEQUENCE OF GAMQosConfigIngressMapEntry
    MAX-ACCESS  not-accessible
    STATUS      current
    DESCRIPTION
        "This table contains the configuration of QoS Ingress Maps. The index is
         IngressMapId.
         
         This is an optional table and is only present if
         qosCapabilitiesHasIngressMap is true."
    ::= { gamQosConfigIngressMap 1 }

gamQosConfigIngressMapEntry OBJECT-TYPE
    SYNTAX      GAMQosConfigIngressMapEntry
    MAX-ACCESS  not-accessible
    STATUS      current
    DESCRIPTION
        "Each row contains the configuration of Key and Action values for a
         single QoS Ingress Map."
    INDEX       { gamQosConfigIngressMapIngressMapId }
    ::= { gamQosConfigIngressMapTable 1 }

GAMQosConfigIngressMapEntry ::= SEQUENCE {
    gamQosConfigIngressMapIngressMapId  Integer32,
    gamQosConfigIngressMapKey           GAMQosIngressMapKey,
    gamQosConfigIngressMapActionCos     TruthValue,
    gamQosConfigIngressMapActionDpl     TruthValue,
    gamQosConfigIngressMapActionPcp     TruthValue,
    gamQosConfigIngressMapActionDei     TruthValue,
    gamQosConfigIngressMapActionDscp    TruthValue,
    gamQosConfigIngressMapActionCosid   TruthValue,
    gamQosConfigIngressMapActionPath    TruthValue,
    gamQosConfigIngressMapAction        GAMRowEditorState
}

gamQosConfigIngressMapIngressMapId OBJECT-TYPE
    SYNTAX      Integer32 (0..2147483647)
    MAX-ACCESS  accessible-for-notify
    STATUS      current
    DESCRIPTION
        "Ingress Map Id.
         
         Valid range is
         qosCapabilitiesIngressMapIdMin-qosCapabilitiesIngressMapIdMax.
         
         
         
         This object is only available if the capability object
         'gamQosCapabilitiesHasIngressMap' is True."
    ::= { gamQosConfigIngressMapEntry 1 }

gamQosConfigIngressMapKey OBJECT-TYPE
    SYNTAX      GAMQosIngressMapKey
    MAX-ACCESS  read-write
    STATUS      current
    DESCRIPTION
        "An integer that indicates the key to use when matching frames in the
         ingress map. If the value is pcp(0), use classified PCP value as key
         (default).
         
         If the value is pcpDei(1), use classified PCP and DEI values as key.
         
         If the value is dscp(2), use the frame's DSCP value as key. For non-IP
         frames, no mapping is done.
         
         If the value is dscpPcpDei(3), use the frame's DSCP value as key. For
         non-IP frames, use classified PCP and DEI values as key.
         
         This object is only available if the capability object
         'gamQosCapabilitiesHasIngressMap' is True."
    ::= { gamQosConfigIngressMapEntry 2 }

gamQosConfigIngressMapActionCos OBJECT-TYPE
    SYNTAX      TruthValue
    MAX-ACCESS  read-write
    STATUS      current
    DESCRIPTION
        "If true, enable classification of CoS.
         
         This object is only available if the capability object
         'gamQosCapabilitiesHasIngressMap' is True."
    ::= { gamQosConfigIngressMapEntry 3 }

gamQosConfigIngressMapActionDpl OBJECT-TYPE
    SYNTAX      TruthValue
    MAX-ACCESS  read-write
    STATUS      current
    DESCRIPTION
        "If true, enable classification of DPL.
         
         This object is only available if the capability object
         'gamQosCapabilitiesHasIngressMap' is True."
    ::= { gamQosConfigIngressMapEntry 4 }

gamQosConfigIngressMapActionPcp OBJECT-TYPE
    SYNTAX      TruthValue
    MAX-ACCESS  read-write
    STATUS      current
    DESCRIPTION
        "If true, enable classification of PCP.
         
         This object is only available if the capability object
         'gamQosCapabilitiesHasIngressMap' is True."
    ::= { gamQosConfigIngressMapEntry 5 }

gamQosConfigIngressMapActionDei OBJECT-TYPE
    SYNTAX      TruthValue
    MAX-ACCESS  read-write
    STATUS      current
    DESCRIPTION
        "If true, enable classification of DEI.
         
         This object is only available if the capability object
         'gamQosCapabilitiesHasIngressMap' is True."
    ::= { gamQosConfigIngressMapEntry 6 }

gamQosConfigIngressMapActionDscp OBJECT-TYPE
    SYNTAX      TruthValue
    MAX-ACCESS  read-write
    STATUS      current
    DESCRIPTION
        "If true, enable classification of DSCP.
         
         This object is only available if the capability object
         'gamQosCapabilitiesHasIngressMap' is True."
    ::= { gamQosConfigIngressMapEntry 7 }

gamQosConfigIngressMapActionCosid OBJECT-TYPE
    SYNTAX      TruthValue
    MAX-ACCESS  read-write
    STATUS      current
    DESCRIPTION
        "If true, enable classification of COSID.
         
         This object is only available if the capability object
         'gamQosCapabilitiesHasIngressMap' is True."
    ::= { gamQosConfigIngressMapEntry 8 }

gamQosConfigIngressMapActionPath OBJECT-TYPE
    SYNTAX      TruthValue
    MAX-ACCESS  read-write
    STATUS      current
    DESCRIPTION
        "If true, enable classification of PATH-COSID.
         
         This object is only available if the capability object
         'gamQosCapabilitiesHasIngressMap' is True."
    ::= { gamQosConfigIngressMapEntry 9 }

gamQosConfigIngressMapAction OBJECT-TYPE
    SYNTAX      GAMRowEditorState
    MAX-ACCESS  read-write
    STATUS      current
    DESCRIPTION
        "Action
         
         This object is only available if the capability object
         'gamQosCapabilitiesHasIngressMap' is True."
    ::= { gamQosConfigIngressMapEntry 10000 }

gamQosConfigIngressMapTableRowEditor OBJECT IDENTIFIER
    ::= { gamQosConfigIngressMap 2 }

gamQosConfigIngressMapTableRowEditorIngressMapId OBJECT-TYPE
    SYNTAX      Integer32 (0..2147483647)
    MAX-ACCESS  read-write
    STATUS      current
    DESCRIPTION
        "Ingress Map Id.
         
         Valid range is
         qosCapabilitiesIngressMapIdMin-qosCapabilitiesIngressMapIdMax.
         
         
         
         This object is only available if the capability object
         'gamQosCapabilitiesHasIngressMap' is True."
    ::= { gamQosConfigIngressMapTableRowEditor 1 }

gamQosConfigIngressMapTableRowEditorKey OBJECT-TYPE
    SYNTAX      GAMQosIngressMapKey
    MAX-ACCESS  read-write
    STATUS      current
    DESCRIPTION
        "An integer that indicates the key to use when matching frames in the
         ingress map. If the value is pcp(0), use classified PCP value as key
         (default).
         
         If the value is pcpDei(1), use classified PCP and DEI values as key.
         
         If the value is dscp(2), use the frame's DSCP value as key. For non-IP
         frames, no mapping is done.
         
         If the value is dscpPcpDei(3), use the frame's DSCP value as key. For
         non-IP frames, use classified PCP and DEI values as key.
         
         This object is only available if the capability object
         'gamQosCapabilitiesHasIngressMap' is True."
    ::= { gamQosConfigIngressMapTableRowEditor 2 }

gamQosConfigIngressMapTableRowEditorActionCos OBJECT-TYPE
    SYNTAX      TruthValue
    MAX-ACCESS  read-write
    STATUS      current
    DESCRIPTION
        "If true, enable classification of CoS.
         
         This object is only available if the capability object
         'gamQosCapabilitiesHasIngressMap' is True."
    ::= { gamQosConfigIngressMapTableRowEditor 3 }

gamQosConfigIngressMapTableRowEditorActionDpl OBJECT-TYPE
    SYNTAX      TruthValue
    MAX-ACCESS  read-write
    STATUS      current
    DESCRIPTION
        "If true, enable classification of DPL.
         
         This object is only available if the capability object
         'gamQosCapabilitiesHasIngressMap' is True."
    ::= { gamQosConfigIngressMapTableRowEditor 4 }

gamQosConfigIngressMapTableRowEditorActionPcp OBJECT-TYPE
    SYNTAX      TruthValue
    MAX-ACCESS  read-write
    STATUS      current
    DESCRIPTION
        "If true, enable classification of PCP.
         
         This object is only available if the capability object
         'gamQosCapabilitiesHasIngressMap' is True."
    ::= { gamQosConfigIngressMapTableRowEditor 5 }

gamQosConfigIngressMapTableRowEditorActionDei OBJECT-TYPE
    SYNTAX      TruthValue
    MAX-ACCESS  read-write
    STATUS      current
    DESCRIPTION
        "If true, enable classification of DEI.
         
         This object is only available if the capability object
         'gamQosCapabilitiesHasIngressMap' is True."
    ::= { gamQosConfigIngressMapTableRowEditor 6 }

gamQosConfigIngressMapTableRowEditorActionDscp OBJECT-TYPE
    SYNTAX      TruthValue
    MAX-ACCESS  read-write
    STATUS      current
    DESCRIPTION
        "If true, enable classification of DSCP.
         
         This object is only available if the capability object
         'gamQosCapabilitiesHasIngressMap' is True."
    ::= { gamQosConfigIngressMapTableRowEditor 7 }

gamQosConfigIngressMapTableRowEditorActionCosid OBJECT-TYPE
    SYNTAX      TruthValue
    MAX-ACCESS  read-write
    STATUS      current
    DESCRIPTION
        "If true, enable classification of COSID.
         
         This object is only available if the capability object
         'gamQosCapabilitiesHasIngressMap' is True."
    ::= { gamQosConfigIngressMapTableRowEditor 8 }

gamQosConfigIngressMapTableRowEditorActionPath OBJECT-TYPE
    SYNTAX      TruthValue
    MAX-ACCESS  read-write
    STATUS      current
    DESCRIPTION
        "If true, enable classification of PATH-COSID.
         
         This object is only available if the capability object
         'gamQosCapabilitiesHasIngressMap' is True."
    ::= { gamQosConfigIngressMapTableRowEditor 9 }

gamQosConfigIngressMapTableRowEditorAction OBJECT-TYPE
    SYNTAX      GAMRowEditorState
    MAX-ACCESS  read-write
    STATUS      current
    DESCRIPTION
        "Action
         
         This object is only available if the capability object
         'gamQosCapabilitiesHasIngressMap' is True."
    ::= { gamQosConfigIngressMapTableRowEditor 10000 }

gamQosConfigIngressMapPcpTable OBJECT-TYPE
    SYNTAX      SEQUENCE OF GAMQosConfigIngressMapPcpEntry
    MAX-ACCESS  not-accessible
    STATUS      current
    DESCRIPTION
        "This table contains the configuration of QoS Ingress Maps entries.
         
         This is an optional table and is only present if
         qosCapabilitiesHasIngressMap is true."
    ::= { gamQosConfigIngressMap 3 }

gamQosConfigIngressMapPcpEntry OBJECT-TYPE
    SYNTAX      GAMQosConfigIngressMapPcpEntry
    MAX-ACCESS  not-accessible
    STATUS      current
    DESCRIPTION
        "Each row contains the configuration of a single entry in a QoS Ingress
         Map with PCP and DEI as index."
    INDEX       { gamQosConfigIngressMapPcpIngressMapId,
                  gamQosConfigIngressMapPcpPcp,
                  gamQosConfigIngressMapPcpDei }
    ::= { gamQosConfigIngressMapPcpTable 1 }

GAMQosConfigIngressMapPcpEntry ::= SEQUENCE {
    gamQosConfigIngressMapPcpIngressMapId  Integer32,
    gamQosConfigIngressMapPcpPcp           Integer32,
    gamQosConfigIngressMapPcpDei           Integer32,
    gamQosConfigIngressMapPcpToCos         GAMUnsigned8,
    gamQosConfigIngressMapPcpToDpl         GAMUnsigned8,
    gamQosConfigIngressMapPcpToPcp         GAMUnsigned8,
    gamQosConfigIngressMapPcpToDei         GAMUnsigned8,
    gamQosConfigIngressMapPcpToDscp        Dscp,
    gamQosConfigIngressMapPcpToCosid       GAMUnsigned8,
    gamQosConfigIngressMapPcpToPathCosid   GAMUnsigned8
}

gamQosConfigIngressMapPcpIngressMapId OBJECT-TYPE
    SYNTAX      Integer32 (0..2147483647)
    MAX-ACCESS  accessible-for-notify
    STATUS      current
    DESCRIPTION
        "Ingress Map Id.
         
         Valid range is
         qosCapabilitiesIngressMapIdMin-qosCapabilitiesIngressMapIdMax.
         
         
         
         This object is only available if the capability object
         'gamQosCapabilitiesHasIngressMap' is True."
    ::= { gamQosConfigIngressMapPcpEntry 1 }

gamQosConfigIngressMapPcpPcp OBJECT-TYPE
    SYNTAX      Integer32 (0..7)
    MAX-ACCESS  accessible-for-notify
    STATUS      current
    DESCRIPTION
        "PCP index.
         
         This object is only available if the capability object
         'gamQosCapabilitiesHasIngressMap' is True."
    ::= { gamQosConfigIngressMapPcpEntry 2 }

gamQosConfigIngressMapPcpDei OBJECT-TYPE
    SYNTAX      Integer32 (0..1)
    MAX-ACCESS  accessible-for-notify
    STATUS      current
    DESCRIPTION
        "DEI index.
         
         This object is only available if the capability object
         'gamQosCapabilitiesHasIngressMap' is True."
    ::= { gamQosConfigIngressMapPcpEntry 3 }

gamQosConfigIngressMapPcpToCos OBJECT-TYPE
    SYNTAX      GAMUnsigned8
    MAX-ACCESS  read-write
    STATUS      current
    DESCRIPTION
        "Setup the mapped CoS value.
         
         Valid range is qosCapabilitiesClassMin-qosCapabilitiesClassMax.
         
         This object is only available if the capability object
         'gamQosCapabilitiesHasIngressMap' is True."
    ::= { gamQosConfigIngressMapPcpEntry 4 }

gamQosConfigIngressMapPcpToDpl OBJECT-TYPE
    SYNTAX      GAMUnsigned8
    MAX-ACCESS  read-write
    STATUS      current
    DESCRIPTION
        "Setup the mapped DPL (Drop Precedence Level) value.
         
         Valid range is qosCapabilitiesDplMin-qosCapabilitiesDplMax.
         
         This object is only available if the capability object
         'gamQosCapabilitiesHasIngressMap' is True."
    ::= { gamQosConfigIngressMapPcpEntry 5 }

gamQosConfigIngressMapPcpToPcp OBJECT-TYPE
    SYNTAX      GAMUnsigned8
    MAX-ACCESS  read-write
    STATUS      current
    DESCRIPTION
        "Setup the mapped PCP value.
         
         Valid range is 0-7.
         
         
         
         This object is only available if the capability object
         'gamQosCapabilitiesHasIngressMap' is True."
    ::= { gamQosConfigIngressMapPcpEntry 6 }

gamQosConfigIngressMapPcpToDei OBJECT-TYPE
    SYNTAX      GAMUnsigned8
    MAX-ACCESS  read-write
    STATUS      current
    DESCRIPTION
        "Setup the mapped DEI value.
         
         Valid range is 0-1.
         
         
         
         This object is only available if the capability object
         'gamQosCapabilitiesHasIngressMap' is True."
    ::= { gamQosConfigIngressMapPcpEntry 7 }

gamQosConfigIngressMapPcpToDscp OBJECT-TYPE
    SYNTAX      Dscp
    MAX-ACCESS  read-write
    STATUS      current
    DESCRIPTION
        "Setup the mapped DSCP value.
         
         Valid range is 0-63.
         
         
         
         This object is only available if the capability object
         'gamQosCapabilitiesHasIngressMap' is True."
    ::= { gamQosConfigIngressMapPcpEntry 8 }

gamQosConfigIngressMapPcpToCosid OBJECT-TYPE
    SYNTAX      GAMUnsigned8
    MAX-ACCESS  read-write
    STATUS      current
    DESCRIPTION
        "Setup the mapped COSID value.
         
         Valid range is qosCapabilitiesCosIdMin-qosCapabilitiesCosIdMax.
         
         
         
         This object is only available if the capability object
         'gamQosCapabilitiesHasIngressMap' is True."
    ::= { gamQosConfigIngressMapPcpEntry 9 }

gamQosConfigIngressMapPcpToPathCosid OBJECT-TYPE
    SYNTAX      GAMUnsigned8
    MAX-ACCESS  read-write
    STATUS      current
    DESCRIPTION
        "Setup the mapped PATH-COSID value.
         
         Valid range is qosCapabilitiesCosIdMin-qosCapabilitiesCosIdMax.
         
         
         
         This object is only available if the capability object
         'gamQosCapabilitiesHasIngressMap' is True."
    ::= { gamQosConfigIngressMapPcpEntry 10 }

gamQosConfigIngressMapDscpTable OBJECT-TYPE
    SYNTAX      SEQUENCE OF GAMQosConfigIngressMapDscpEntry
    MAX-ACCESS  not-accessible
    STATUS      current
    DESCRIPTION
        "This table contains the configuration of QoS Ingress Maps entries.
         
         This is an optional table and is only present if
         qosCapabilitiesHasIngressMap is true."
    ::= { gamQosConfigIngressMap 4 }

gamQosConfigIngressMapDscpEntry OBJECT-TYPE
    SYNTAX      GAMQosConfigIngressMapDscpEntry
    MAX-ACCESS  not-accessible
    STATUS      current
    DESCRIPTION
        "Each row contains the configuration of a single entry in a QoS Ingress
         Map with DSCP as index."
    INDEX       { gamQosConfigIngressMapDscpIngressMapId,
                  gamQosConfigIngressMapDscpDscp }
    ::= { gamQosConfigIngressMapDscpTable 1 }

GAMQosConfigIngressMapDscpEntry ::= SEQUENCE {
    gamQosConfigIngressMapDscpIngressMapId  Integer32,
    gamQosConfigIngressMapDscpDscp          Dscp,
    gamQosConfigIngressMapDscpToCos         GAMUnsigned8,
    gamQosConfigIngressMapDscpToDpl         GAMUnsigned8,
    gamQosConfigIngressMapDscpToPcp         GAMUnsigned8,
    gamQosConfigIngressMapDscpToDei         GAMUnsigned8,
    gamQosConfigIngressMapDscpToDscp        Dscp,
    gamQosConfigIngressMapDscpToCosid       GAMUnsigned8,
    gamQosConfigIngressMapDscpToPathCosid   GAMUnsigned8
}

gamQosConfigIngressMapDscpIngressMapId OBJECT-TYPE
    SYNTAX      Integer32 (0..2147483647)
    MAX-ACCESS  accessible-for-notify
    STATUS      current
    DESCRIPTION
        "Ingress Map Id.
         
         Valid range is
         qosCapabilitiesIngressMapIdMin-qosCapabilitiesIngressMapIdMax.
         
         
         
         This object is only available if the capability object
         'gamQosCapabilitiesHasIngressMap' is True."
    ::= { gamQosConfigIngressMapDscpEntry 1 }

gamQosConfigIngressMapDscpDscp OBJECT-TYPE
    SYNTAX      Dscp
    MAX-ACCESS  accessible-for-notify
    STATUS      current
    DESCRIPTION
        "DSCP index.
         
         This object is only available if the capability object
         'gamQosCapabilitiesHasIngressMap' is True."
    ::= { gamQosConfigIngressMapDscpEntry 2 }

gamQosConfigIngressMapDscpToCos OBJECT-TYPE
    SYNTAX      GAMUnsigned8
    MAX-ACCESS  read-write
    STATUS      current
    DESCRIPTION
        "Setup the mapped CoS value.
         
         Valid range is qosCapabilitiesClassMin-qosCapabilitiesClassMax.
         
         This object is only available if the capability object
         'gamQosCapabilitiesHasIngressMap' is True."
    ::= { gamQosConfigIngressMapDscpEntry 3 }

gamQosConfigIngressMapDscpToDpl OBJECT-TYPE
    SYNTAX      GAMUnsigned8
    MAX-ACCESS  read-write
    STATUS      current
    DESCRIPTION
        "Setup the mapped DPL (Drop Precedence Level) value.
         
         Valid range is qosCapabilitiesDplMin-qosCapabilitiesDplMax.
         
         This object is only available if the capability object
         'gamQosCapabilitiesHasIngressMap' is True."
    ::= { gamQosConfigIngressMapDscpEntry 4 }

gamQosConfigIngressMapDscpToPcp OBJECT-TYPE
    SYNTAX      GAMUnsigned8
    MAX-ACCESS  read-write
    STATUS      current
    DESCRIPTION
        "Setup the mapped PCP value.
         
         Valid range is 0-7.
         
         
         
         This object is only available if the capability object
         'gamQosCapabilitiesHasIngressMap' is True."
    ::= { gamQosConfigIngressMapDscpEntry 5 }

gamQosConfigIngressMapDscpToDei OBJECT-TYPE
    SYNTAX      GAMUnsigned8
    MAX-ACCESS  read-write
    STATUS      current
    DESCRIPTION
        "Setup the mapped DEI value.
         
         Valid range is 0-1.
         
         
         
         This object is only available if the capability object
         'gamQosCapabilitiesHasIngressMap' is True."
    ::= { gamQosConfigIngressMapDscpEntry 6 }

gamQosConfigIngressMapDscpToDscp OBJECT-TYPE
    SYNTAX      Dscp
    MAX-ACCESS  read-write
    STATUS      current
    DESCRIPTION
        "Setup the mapped DSCP value.
         
         Valid range is 0-63.
         
         
         
         This object is only available if the capability object
         'gamQosCapabilitiesHasIngressMap' is True."
    ::= { gamQosConfigIngressMapDscpEntry 7 }

gamQosConfigIngressMapDscpToCosid OBJECT-TYPE
    SYNTAX      GAMUnsigned8
    MAX-ACCESS  read-write
    STATUS      current
    DESCRIPTION
        "Setup the mapped COSID value.
         
         Valid range is qosCapabilitiesCosIdMin-qosCapabilitiesCosIdMax.
         
         
         
         This object is only available if the capability object
         'gamQosCapabilitiesHasIngressMap' is True."
    ::= { gamQosConfigIngressMapDscpEntry 8 }

gamQosConfigIngressMapDscpToPathCosid OBJECT-TYPE
    SYNTAX      GAMUnsigned8
    MAX-ACCESS  read-write
    STATUS      current
    DESCRIPTION
        "Setup the mapped PATH-COSID value.
         
         Valid range is qosCapabilitiesCosIdMin-qosCapabilitiesCosIdMax.
         
         
         
         This object is only available if the capability object
         'gamQosCapabilitiesHasIngressMap' is True."
    ::= { gamQosConfigIngressMapDscpEntry 9 }

gamQosConfigEgressMap OBJECT IDENTIFIER
    ::= { gamQosConfig 5 }

gamQosConfigEgressMapTable OBJECT-TYPE
    SYNTAX      SEQUENCE OF GAMQosConfigEgressMapEntry
    MAX-ACCESS  not-accessible
    STATUS      current
    DESCRIPTION
        "This table contains the configuration of Egress Maps. The index is
         EgressMapId.
         
         This is an optional table and is only present if
         qosCapabilitiesHasEgressMap is true."
    ::= { gamQosConfigEgressMap 1 }

gamQosConfigEgressMapEntry OBJECT-TYPE
    SYNTAX      GAMQosConfigEgressMapEntry
    MAX-ACCESS  not-accessible
    STATUS      current
    DESCRIPTION
        "Each row contains the configuration of key and Action values for a
         single Egress Map."
    INDEX       { gamQosConfigEgressMapEgressMapId }
    ::= { gamQosConfigEgressMapTable 1 }

GAMQosConfigEgressMapEntry ::= SEQUENCE {
    gamQosConfigEgressMapEgressMapId  Integer32,
    gamQosConfigEgressMapKey          GAMQosEgressMapKey,
    gamQosConfigEgressMapActionPcp    TruthValue,
    gamQosConfigEgressMapActionDei    TruthValue,
    gamQosConfigEgressMapActionDscp   TruthValue,
    gamQosConfigEgressMapActionPath   TruthValue,
    gamQosConfigEgressMapAction       GAMRowEditorState
}

gamQosConfigEgressMapEgressMapId OBJECT-TYPE
    SYNTAX      Integer32 (0..2147483647)
    MAX-ACCESS  accessible-for-notify
    STATUS      current
    DESCRIPTION
        "Egress Map Id.
         
         Valid range is
         qosCapabilitiesEgressMapIdMin-qosCapabilitiesEgressMapIdMax.
         
         
         
         This object is only available if the capability object
         'gamQosCapabilitiesHasEgressMap' is True."
    ::= { gamQosConfigEgressMapEntry 1 }

gamQosConfigEgressMapKey OBJECT-TYPE
    SYNTAX      GAMQosEgressMapKey
    MAX-ACCESS  read-write
    STATUS      current
    DESCRIPTION
        "An integer that indicates the key to use when matching frames in the
         egress map.
         
         If the value is cosid(0), use classified COSID.
         
         If the value is cosidDpl(1), use classified COSID and DPL.
         
         If the value is dscp(2), use classified DSCP.
         
         If the value is dscpDpl(3), use classified DSCP and DPL.
         
         This object is only available if the capability object
         'gamQosCapabilitiesHasEgressMap' is True."
    ::= { gamQosConfigEgressMapEntry 2 }

gamQosConfigEgressMapActionPcp OBJECT-TYPE
    SYNTAX      TruthValue
    MAX-ACCESS  read-write
    STATUS      current
    DESCRIPTION
        "If true, enable rewriting of PCP.
         
         This object is only available if the capability object
         'gamQosCapabilitiesHasEgressMap' is True."
    ::= { gamQosConfigEgressMapEntry 3 }

gamQosConfigEgressMapActionDei OBJECT-TYPE
    SYNTAX      TruthValue
    MAX-ACCESS  read-write
    STATUS      current
    DESCRIPTION
        "If true, enable rewriting of DEI.
         
         This object is only available if the capability object
         'gamQosCapabilitiesHasEgressMap' is True."
    ::= { gamQosConfigEgressMapEntry 4 }

gamQosConfigEgressMapActionDscp OBJECT-TYPE
    SYNTAX      TruthValue
    MAX-ACCESS  read-write
    STATUS      current
    DESCRIPTION
        "If true, enable rewriting of DSCP.
         
         This object is only available if the capability object
         'gamQosCapabilitiesHasEgressMap' is True."
    ::= { gamQosConfigEgressMapEntry 5 }

gamQosConfigEgressMapActionPath OBJECT-TYPE
    SYNTAX      TruthValue
    MAX-ACCESS  read-write
    STATUS      current
    DESCRIPTION
        "If true, enable rewriting of PATH-COSID.
         
         This object is only available if the capability object
         'gamQosCapabilitiesHasEgressMap' is True."
    ::= { gamQosConfigEgressMapEntry 6 }

gamQosConfigEgressMapAction OBJECT-TYPE
    SYNTAX      GAMRowEditorState
    MAX-ACCESS  read-write
    STATUS      current
    DESCRIPTION
        "Action
         
         This object is only available if the capability object
         'gamQosCapabilitiesHasEgressMap' is True."
    ::= { gamQosConfigEgressMapEntry 10000 }

gamQosConfigEgressMapTableRowEditor OBJECT IDENTIFIER
    ::= { gamQosConfigEgressMap 2 }

gamQosConfigEgressMapTableRowEditorEgressMapId OBJECT-TYPE
    SYNTAX      Integer32 (0..2147483647)
    MAX-ACCESS  read-write
    STATUS      current
    DESCRIPTION
        "Egress Map Id.
         
         Valid range is
         qosCapabilitiesEgressMapIdMin-qosCapabilitiesEgressMapIdMax.
         
         
         
         This object is only available if the capability object
         'gamQosCapabilitiesHasEgressMap' is True."
    ::= { gamQosConfigEgressMapTableRowEditor 1 }

gamQosConfigEgressMapTableRowEditorKey OBJECT-TYPE
    SYNTAX      GAMQosEgressMapKey
    MAX-ACCESS  read-write
    STATUS      current
    DESCRIPTION
        "An integer that indicates the key to use when matching frames in the
         egress map.
         
         If the value is cosid(0), use classified COSID.
         
         If the value is cosidDpl(1), use classified COSID and DPL.
         
         If the value is dscp(2), use classified DSCP.
         
         If the value is dscpDpl(3), use classified DSCP and DPL.
         
         This object is only available if the capability object
         'gamQosCapabilitiesHasEgressMap' is True."
    ::= { gamQosConfigEgressMapTableRowEditor 2 }

gamQosConfigEgressMapTableRowEditorActionPcp OBJECT-TYPE
    SYNTAX      TruthValue
    MAX-ACCESS  read-write
    STATUS      current
    DESCRIPTION
        "If true, enable rewriting of PCP.
         
         This object is only available if the capability object
         'gamQosCapabilitiesHasEgressMap' is True."
    ::= { gamQosConfigEgressMapTableRowEditor 3 }

gamQosConfigEgressMapTableRowEditorActionDei OBJECT-TYPE
    SYNTAX      TruthValue
    MAX-ACCESS  read-write
    STATUS      current
    DESCRIPTION
        "If true, enable rewriting of DEI.
         
         This object is only available if the capability object
         'gamQosCapabilitiesHasEgressMap' is True."
    ::= { gamQosConfigEgressMapTableRowEditor 4 }

gamQosConfigEgressMapTableRowEditorActionDscp OBJECT-TYPE
    SYNTAX      TruthValue
    MAX-ACCESS  read-write
    STATUS      current
    DESCRIPTION
        "If true, enable rewriting of DSCP.
         
         This object is only available if the capability object
         'gamQosCapabilitiesHasEgressMap' is True."
    ::= { gamQosConfigEgressMapTableRowEditor 5 }

gamQosConfigEgressMapTableRowEditorActionPath OBJECT-TYPE
    SYNTAX      TruthValue
    MAX-ACCESS  read-write
    STATUS      current
    DESCRIPTION
        "If true, enable rewriting of PATH-COSID.
         
         This object is only available if the capability object
         'gamQosCapabilitiesHasEgressMap' is True."
    ::= { gamQosConfigEgressMapTableRowEditor 6 }

gamQosConfigEgressMapTableRowEditorAction OBJECT-TYPE
    SYNTAX      GAMRowEditorState
    MAX-ACCESS  read-write
    STATUS      current
    DESCRIPTION
        "Action
         
         This object is only available if the capability object
         'gamQosCapabilitiesHasEgressMap' is True."
    ::= { gamQosConfigEgressMapTableRowEditor 10000 }

gamQosConfigEgressMapCosidTable OBJECT-TYPE
    SYNTAX      SEQUENCE OF GAMQosConfigEgressMapCosidEntry
    MAX-ACCESS  not-accessible
    STATUS      current
    DESCRIPTION
        "This table contains the configuration of QoS Egress Maps entries.
         
         This is an optional table and is only present if
         qosCapabilitiesHasEgressMap is true."
    ::= { gamQosConfigEgressMap 3 }

gamQosConfigEgressMapCosidEntry OBJECT-TYPE
    SYNTAX      GAMQosConfigEgressMapCosidEntry
    MAX-ACCESS  not-accessible
    STATUS      current
    DESCRIPTION
        "Each row contains the configuration of a single entry in a QoS Egress
         Map with COSID and DPL as index."
    INDEX       { gamQosConfigEgressMapCosidEgressMapId,
                  gamQosConfigEgressMapCosidCosid,
                  gamQosConfigEgressMapCosidDpl }
    ::= { gamQosConfigEgressMapCosidTable 1 }

GAMQosConfigEgressMapCosidEntry ::= SEQUENCE {
    gamQosConfigEgressMapCosidEgressMapId  Integer32,
    gamQosConfigEgressMapCosidCosid        Integer32,
    gamQosConfigEgressMapCosidDpl          Integer32,
    gamQosConfigEgressMapCosidToPcp        GAMUnsigned8,
    gamQosConfigEgressMapCosidToDei        GAMUnsigned8,
    gamQosConfigEgressMapCosidToDscp       Dscp,
    gamQosConfigEgressMapCosidToPathCosid  GAMUnsigned8
}

gamQosConfigEgressMapCosidEgressMapId OBJECT-TYPE
    SYNTAX      Integer32 (0..2147483647)
    MAX-ACCESS  accessible-for-notify
    STATUS      current
    DESCRIPTION
        "Egress Map Id.
         
         Valid range is
         qosCapabilitiesEgressMapIdMin-qosCapabilitiesEgressMapIdMax.
         
         
         
         This object is only available if the capability object
         'gamQosCapabilitiesHasEgressMap' is True."
    ::= { gamQosConfigEgressMapCosidEntry 1 }

gamQosConfigEgressMapCosidCosid OBJECT-TYPE
    SYNTAX      Integer32 (0..7)
    MAX-ACCESS  accessible-for-notify
    STATUS      current
    DESCRIPTION
        "COSID index.
         
         This object is only available if the capability object
         'gamQosCapabilitiesHasEgressMap' is True."
    ::= { gamQosConfigEgressMapCosidEntry 2 }

gamQosConfigEgressMapCosidDpl OBJECT-TYPE
    SYNTAX      Integer32 (0..3)
    MAX-ACCESS  accessible-for-notify
    STATUS      current
    DESCRIPTION
        "DPL index.
         
         This object is only available if the capability object
         'gamQosCapabilitiesHasEgressMap' is True."
    ::= { gamQosConfigEgressMapCosidEntry 3 }

gamQosConfigEgressMapCosidToPcp OBJECT-TYPE
    SYNTAX      GAMUnsigned8
    MAX-ACCESS  read-write
    STATUS      current
    DESCRIPTION
        "Setup the mapped PCP value.
         
         Valid range is 0-7.
         
         
         
         This object is only available if the capability object
         'gamQosCapabilitiesHasEgressMap' is True."
    ::= { gamQosConfigEgressMapCosidEntry 4 }

gamQosConfigEgressMapCosidToDei OBJECT-TYPE
    SYNTAX      GAMUnsigned8
    MAX-ACCESS  read-write
    STATUS      current
    DESCRIPTION
        "Setup the mapped DEI value.
         
         Valid range is 0-1.
         
         
         
         This object is only available if the capability object
         'gamQosCapabilitiesHasEgressMap' is True."
    ::= { gamQosConfigEgressMapCosidEntry 5 }

gamQosConfigEgressMapCosidToDscp OBJECT-TYPE
    SYNTAX      Dscp
    MAX-ACCESS  read-write
    STATUS      current
    DESCRIPTION
        "Setup the mapped DSCP value.
         
         Valid range is 0-63.
         
         
         
         This object is only available if the capability object
         'gamQosCapabilitiesHasEgressMap' is True."
    ::= { gamQosConfigEgressMapCosidEntry 6 }

gamQosConfigEgressMapCosidToPathCosid OBJECT-TYPE
    SYNTAX      GAMUnsigned8
    MAX-ACCESS  read-write
    STATUS      current
    DESCRIPTION
        "Setup the mapped PATH-COSID value.
         
         Valid range is qosCapabilitiesCosIdMin-qosCapabilitiesCosIdMax.
         
         
         
         This object is only available if the capability object
         'gamQosCapabilitiesHasEgressMap' is True."
    ::= { gamQosConfigEgressMapCosidEntry 7 }

gamQosConfigEgressMapDscpTable OBJECT-TYPE
    SYNTAX      SEQUENCE OF GAMQosConfigEgressMapDscpEntry
    MAX-ACCESS  not-accessible
    STATUS      current
    DESCRIPTION
        "This table contains the configuration of QoS Egress Maps entries.
         
         This is an optional table and is only present if
         qosCapabilitiesHasEgressMap is true."
    ::= { gamQosConfigEgressMap 4 }

gamQosConfigEgressMapDscpEntry OBJECT-TYPE
    SYNTAX      GAMQosConfigEgressMapDscpEntry
    MAX-ACCESS  not-accessible
    STATUS      current
    DESCRIPTION
        "Each row contains the configuration of a single entry in a QoS Egress
         Map with DSCP and DPL as index."
    INDEX       { gamQosConfigEgressMapDscpEgressMapId,
                  gamQosConfigEgressMapDscpDscp,
                  gamQosConfigEgressMapDscpDpl }
    ::= { gamQosConfigEgressMapDscpTable 1 }

GAMQosConfigEgressMapDscpEntry ::= SEQUENCE {
    gamQosConfigEgressMapDscpEgressMapId  Integer32,
    gamQosConfigEgressMapDscpDscp         Dscp,
    gamQosConfigEgressMapDscpDpl          Integer32,
    gamQosConfigEgressMapDscpToPcp        GAMUnsigned8,
    gamQosConfigEgressMapDscpToDei        GAMUnsigned8,
    gamQosConfigEgressMapDscpToDscp       Dscp,
    gamQosConfigEgressMapDscpToPathCosid  GAMUnsigned8
}

gamQosConfigEgressMapDscpEgressMapId OBJECT-TYPE
    SYNTAX      Integer32 (0..2147483647)
    MAX-ACCESS  accessible-for-notify
    STATUS      current
    DESCRIPTION
        "Egress Map Id.
         
         Valid range is
         qosCapabilitiesEgressMapIdMin-qosCapabilitiesEgressMapIdMax.
         
         
         
         This object is only available if the capability object
         'gamQosCapabilitiesHasEgressMap' is True."
    ::= { gamQosConfigEgressMapDscpEntry 1 }

gamQosConfigEgressMapDscpDscp OBJECT-TYPE
    SYNTAX      Dscp
    MAX-ACCESS  accessible-for-notify
    STATUS      current
    DESCRIPTION
        "DSCP index.
         
         This object is only available if the capability object
         'gamQosCapabilitiesHasEgressMap' is True."
    ::= { gamQosConfigEgressMapDscpEntry 2 }

gamQosConfigEgressMapDscpDpl OBJECT-TYPE
    SYNTAX      Integer32 (0..3)
    MAX-ACCESS  accessible-for-notify
    STATUS      current
    DESCRIPTION
        "DPL index.
         
         This object is only available if the capability object
         'gamQosCapabilitiesHasEgressMap' is True."
    ::= { gamQosConfigEgressMapDscpEntry 3 }

gamQosConfigEgressMapDscpToPcp OBJECT-TYPE
    SYNTAX      GAMUnsigned8
    MAX-ACCESS  read-write
    STATUS      current
    DESCRIPTION
        "Setup the mapped PCP value.
         
         Valid range is 0-7.
         
         
         
         This object is only available if the capability object
         'gamQosCapabilitiesHasEgressMap' is True."
    ::= { gamQosConfigEgressMapDscpEntry 4 }

gamQosConfigEgressMapDscpToDei OBJECT-TYPE
    SYNTAX      GAMUnsigned8
    MAX-ACCESS  read-write
    STATUS      current
    DESCRIPTION
        "Setup the mapped DEI value.
         
         Valid range is 0-1.
         
         
         
         This object is only available if the capability object
         'gamQosCapabilitiesHasEgressMap' is True."
    ::= { gamQosConfigEgressMapDscpEntry 5 }

gamQosConfigEgressMapDscpToDscp OBJECT-TYPE
    SYNTAX      Dscp
    MAX-ACCESS  read-write
    STATUS      current
    DESCRIPTION
        "Setup the mapped DSCP value.
         
         Valid range is 0-63.
         
         
         
         This object is only available if the capability object
         'gamQosCapabilitiesHasEgressMap' is True."
    ::= { gamQosConfigEgressMapDscpEntry 6 }

gamQosConfigEgressMapDscpToPathCosid OBJECT-TYPE
    SYNTAX      GAMUnsigned8
    MAX-ACCESS  read-write
    STATUS      current
    DESCRIPTION
        "Setup the mapped PATH-COSID value.
         
         Valid range is qosCapabilitiesCosIdMin-qosCapabilitiesCosIdMax.
         
         
         
         This object is only available if the capability object
         'gamQosCapabilitiesHasEgressMap' is True."
    ::= { gamQosConfigEgressMapDscpEntry 7 }

gamQosConfigPsfp OBJECT IDENTIFIER
    ::= { gamQosConfig 6 }

gamQosConfigPsfpSfiTable OBJECT-TYPE
    SYNTAX      SEQUENCE OF GAMQosConfigPsfpSfiEntry
    MAX-ACCESS  not-accessible
    STATUS      current
    DESCRIPTION
        "This table contains the configuration of PSFP SFI's. The index is
         SFIId.
         
         This is an optional table and is only present if qosCapabilitiesHasPsfp
         is true."
    ::= { gamQosConfigPsfp 1 }

gamQosConfigPsfpSfiEntry OBJECT-TYPE
    SYNTAX      GAMQosConfigPsfpSfiEntry
    MAX-ACCESS  not-accessible
    STATUS      current
    DESCRIPTION
        "Each row contains the configuration of a single PSFP SFI."
    INDEX       { gamQosConfigPsfpSfiSfiId }
    ::= { gamQosConfigPsfpSfiTable 1 }

GAMQosConfigPsfpSfiEntry ::= SEQUENCE {
    gamQosConfigPsfpSfiSfiId                 Integer32,
    gamQosConfigPsfpSfiStreamHandleSpec      GAMInteger16,
    gamQosConfigPsfpSfiPrioritySpec          GAMInteger8,
    gamQosConfigPsfpSfiInterfaceSpec         GAMInterfaceIndex,
    gamQosConfigPsfpSfiStreamGateInstanceId  GAMUnsigned16,
    gamQosConfigPsfpSfiMaximumSduSize        GAMUnsigned16,
    gamQosConfigPsfpSfiFlowMeterInstanceId   GAMInteger16,
    gamQosConfigPsfpSfiBlockOversizeEnable   TruthValue,
    gamQosConfigPsfpSfiBlockOversize         TruthValue,
    gamQosConfigPsfpSfiAction                GAMRowEditorState
}

gamQosConfigPsfpSfiSfiId OBJECT-TYPE
    SYNTAX      Integer32 (0..2147483647)
    MAX-ACCESS  accessible-for-notify
    STATUS      current
    DESCRIPTION
        "SFI Id.
         
         
         
         This object is only available if the capability object
         'gamQosCapabilitiesHasPsfp' is True."
    ::= { gamQosConfigPsfpSfiEntry 1 }

gamQosConfigPsfpSfiStreamHandleSpec OBJECT-TYPE
    SYNTAX      GAMInteger16
    MAX-ACCESS  read-write
    STATUS      current
    DESCRIPTION
        "The StreamHandleSpec parameter contains a stream identifier
         specification value. A value of -1 denotes the wild card value; zero or
         positive values denote stream identifier val.
         
         This object is only available if the capability object
         'gamQosCapabilitiesHasPsfp' is True."
    ::= { gamQosConfigPsfpSfiEntry 2 }

gamQosConfigPsfpSfiPrioritySpec OBJECT-TYPE
    SYNTAX      GAMInteger8
    MAX-ACCESS  read-write
    STATUS      current
    DESCRIPTION
        "The PrioritySpec parameter contains a priority specification value. A
         value of -1 denotes the wild card value; zero or positive values denote
         priority values.
         
         This object is only available if the capability object
         'gamQosCapabilitiesHasPsfp' is True."
    ::= { gamQosConfigPsfpSfiEntry 3 }

gamQosConfigPsfpSfiInterfaceSpec OBJECT-TYPE
    SYNTAX      GAMInterfaceIndex
    MAX-ACCESS  read-write
    STATUS      current
    DESCRIPTION
        "The InterfaceSpec parameter contains an interface specification value.
         A value of VTSS_IFINDEX_NONE denotes the wild card value.
         
         This object is only available if the capability object
         'gamQosCapabilitiesHasPsfp' is True."
    ::= { gamQosConfigPsfpSfiEntry 4 }

gamQosConfigPsfpSfiStreamGateInstanceId OBJECT-TYPE
    SYNTAX      GAMUnsigned16
    MAX-ACCESS  read-write
    STATUS      current
    DESCRIPTION
        "The StreamGateInstanceID parameter contains the index of an entry in
         the Stream Gate Table.
         
         This object is only available if the capability object
         'gamQosCapabilitiesHasPsfp' is True."
    ::= { gamQosConfigPsfpSfiEntry 5 }

gamQosConfigPsfpSfiMaximumSduSize OBJECT-TYPE
    SYNTAX      GAMUnsigned16
    MAX-ACCESS  read-write
    STATUS      current
    DESCRIPTION
        "The MaximumSDUSize parameter specifies the maximum allowed frame size
         for the stream. Any frame exceeding this value will be dropped. A value
         of 0 denote that the MaximumSDUSize filter is disabled for this stream.
         
         This object is only available if the capability object
         'gamQosCapabilitiesHasPsfp' is True."
    ::= { gamQosConfigPsfpSfiEntry 6 }

gamQosConfigPsfpSfiFlowMeterInstanceId OBJECT-TYPE
    SYNTAX      GAMInteger16
    MAX-ACCESS  read-write
    STATUS      current
    DESCRIPTION
        "The FlowMeterInstanceID parameter contains the index of an entry in the
         Flow Meter Table. A value of -1 denotes that no flow meter is assigned;
         zero or positive values denote flow meter IDs.
         
         This object is only available if the capability object
         'gamQosCapabilitiesHasPsfp' is True."
    ::= { gamQosConfigPsfpSfiEntry 7 }

gamQosConfigPsfpSfiBlockOversizeEnable OBJECT-TYPE
    SYNTAX      TruthValue
    MAX-ACCESS  read-write
    STATUS      current
    DESCRIPTION
        "The StreamBlockedDueToOversizeFrameEnable object contains a Boolean
         value that indicates whether the StreamBlockedDueToOversizeFrame
         function is enabled (TRUE) or disabled (FALSE).
         
         This object is only available if the capability object
         'gamQosCapabilitiesHasPsfp' is True."
    ::= { gamQosConfigPsfpSfiEntry 8 }

gamQosConfigPsfpSfiBlockOversize OBJECT-TYPE
    SYNTAX      TruthValue
    MAX-ACCESS  read-write
    STATUS      current
    DESCRIPTION
        "The StreamBlockedDueToOversizeFrame object contains a Boolean value
         that indicates whether, if the StreamBlockedDueToOversizeFrame function
         is enabled, all frames are to be discarded (TRUE) or not (FALSE).
         
         This object is only available if the capability object
         'gamQosCapabilitiesHasPsfp' is True."
    ::= { gamQosConfigPsfpSfiEntry 9 }

gamQosConfigPsfpSfiAction OBJECT-TYPE
    SYNTAX      GAMRowEditorState
    MAX-ACCESS  read-write
    STATUS      current
    DESCRIPTION
        "Action
         
         This object is only available if the capability object
         'gamQosCapabilitiesHasPsfp' is True."
    ::= { gamQosConfigPsfpSfiEntry 10000 }

gamQosConfigPsfpSfiTableRowEditor OBJECT IDENTIFIER
    ::= { gamQosConfigPsfp 2 }

gamQosConfigPsfpSfiTableRowEditorSfiId OBJECT-TYPE
    SYNTAX      Integer32 (0..2147483647)
    MAX-ACCESS  read-write
    STATUS      current
    DESCRIPTION
        "SFI Id.
         
         
         
         This object is only available if the capability object
         'gamQosCapabilitiesHasPsfp' is True."
    ::= { gamQosConfigPsfpSfiTableRowEditor 1 }

gamQosConfigPsfpSfiTableRowEditorStreamHandleSpec OBJECT-TYPE
    SYNTAX      GAMInteger16
    MAX-ACCESS  read-write
    STATUS      current
    DESCRIPTION
        "The StreamHandleSpec parameter contains a stream identifier
         specification value. A value of -1 denotes the wild card value; zero or
         positive values denote stream identifier val.
         
         This object is only available if the capability object
         'gamQosCapabilitiesHasPsfp' is True."
    ::= { gamQosConfigPsfpSfiTableRowEditor 2 }

gamQosConfigPsfpSfiTableRowEditorPrioritySpec OBJECT-TYPE
    SYNTAX      GAMInteger8
    MAX-ACCESS  read-write
    STATUS      current
    DESCRIPTION
        "The PrioritySpec parameter contains a priority specification value. A
         value of -1 denotes the wild card value; zero or positive values denote
         priority values.
         
         This object is only available if the capability object
         'gamQosCapabilitiesHasPsfp' is True."
    ::= { gamQosConfigPsfpSfiTableRowEditor 3 }

gamQosConfigPsfpSfiTableRowEditorInterfaceSpec OBJECT-TYPE
    SYNTAX      GAMInterfaceIndex
    MAX-ACCESS  read-write
    STATUS      current
    DESCRIPTION
        "The InterfaceSpec parameter contains an interface specification value.
         A value of VTSS_IFINDEX_NONE denotes the wild card value.
         
         This object is only available if the capability object
         'gamQosCapabilitiesHasPsfp' is True."
    ::= { gamQosConfigPsfpSfiTableRowEditor 4 }

gamQosConfigPsfpSfiTableRowEditorStreamGateInstanceId OBJECT-TYPE
    SYNTAX      GAMUnsigned16
    MAX-ACCESS  read-write
    STATUS      current
    DESCRIPTION
        "The StreamGateInstanceID parameter contains the index of an entry in
         the Stream Gate Table.
         
         This object is only available if the capability object
         'gamQosCapabilitiesHasPsfp' is True."
    ::= { gamQosConfigPsfpSfiTableRowEditor 5 }

gamQosConfigPsfpSfiTableRowEditorMaximumSduSize OBJECT-TYPE
    SYNTAX      GAMUnsigned16
    MAX-ACCESS  read-write
    STATUS      current
    DESCRIPTION
        "The MaximumSDUSize parameter specifies the maximum allowed frame size
         for the stream. Any frame exceeding this value will be dropped. A value
         of 0 denote that the MaximumSDUSize filter is disabled for this stream.
         
         This object is only available if the capability object
         'gamQosCapabilitiesHasPsfp' is True."
    ::= { gamQosConfigPsfpSfiTableRowEditor 6 }

gamQosConfigPsfpSfiTableRowEditorFlowMeterInstanceId OBJECT-TYPE
    SYNTAX      GAMInteger16
    MAX-ACCESS  read-write
    STATUS      current
    DESCRIPTION
        "The FlowMeterInstanceID parameter contains the index of an entry in the
         Flow Meter Table. A value of -1 denotes that no flow meter is assigned;
         zero or positive values denote flow meter IDs.
         
         This object is only available if the capability object
         'gamQosCapabilitiesHasPsfp' is True."
    ::= { gamQosConfigPsfpSfiTableRowEditor 7 }

gamQosConfigPsfpSfiTableRowEditorBlockOversizeEnable OBJECT-TYPE
    SYNTAX      TruthValue
    MAX-ACCESS  read-write
    STATUS      current
    DESCRIPTION
        "The StreamBlockedDueToOversizeFrameEnable object contains a Boolean
         value that indicates whether the StreamBlockedDueToOversizeFrame
         function is enabled (TRUE) or disabled (FALSE).
         
         This object is only available if the capability object
         'gamQosCapabilitiesHasPsfp' is True."
    ::= { gamQosConfigPsfpSfiTableRowEditor 8 }

gamQosConfigPsfpSfiTableRowEditorBlockOversize OBJECT-TYPE
    SYNTAX      TruthValue
    MAX-ACCESS  read-write
    STATUS      current
    DESCRIPTION
        "The StreamBlockedDueToOversizeFrame object contains a Boolean value
         that indicates whether, if the StreamBlockedDueToOversizeFrame function
         is enabled, all frames are to be discarded (TRUE) or not (FALSE).
         
         This object is only available if the capability object
         'gamQosCapabilitiesHasPsfp' is True."
    ::= { gamQosConfigPsfpSfiTableRowEditor 9 }

gamQosConfigPsfpSfiTableRowEditorAction OBJECT-TYPE
    SYNTAX      GAMRowEditorState
    MAX-ACCESS  read-write
    STATUS      current
    DESCRIPTION
        "Action
         
         This object is only available if the capability object
         'gamQosCapabilitiesHasPsfp' is True."
    ::= { gamQosConfigPsfpSfiTableRowEditor 10000 }

gamQosConfigPsfpGclTable OBJECT-TYPE
    SYNTAX      SEQUENCE OF GAMQosConfigPsfpGclEntry
    MAX-ACCESS  not-accessible
    STATUS      current
    DESCRIPTION
        "A table containing the admin entries/TLVs of the GCL, as defined in
         IEEE 802.1Qci"
    ::= { gamQosConfigPsfp 3 }

gamQosConfigPsfpGclEntry OBJECT-TYPE
    SYNTAX      GAMQosConfigPsfpGclEntry
    MAX-ACCESS  not-accessible
    STATUS      current
    DESCRIPTION
        "Each row contains single GCL entry with a unique gcl_index"
    INDEX       { gamQosConfigPsfpGclSgiId, gamQosConfigPsfpGclGclId }
    ::= { gamQosConfigPsfpGclTable 1 }

GAMQosConfigPsfpGclEntry ::= SEQUENCE {
    gamQosConfigPsfpGclSgiId         Integer32,
    gamQosConfigPsfpGclGclId         Integer32,
    gamQosConfigPsfpGclGateState     TruthValue,
    gamQosConfigPsfpGclIPV           GAMInteger8,
    gamQosConfigPsfpGclTimeInterval  Unsigned32,
    gamQosConfigPsfpGclOctetMax      Unsigned32
}

gamQosConfigPsfpGclSgiId OBJECT-TYPE
    SYNTAX      Integer32 (0..2147483647)
    MAX-ACCESS  accessible-for-notify
    STATUS      current
    DESCRIPTION
        "SGI Id.
         
         
         
         This object is only available if the capability object
         'gamQosCapabilitiesHasPsfp' is True."
    ::= { gamQosConfigPsfpGclEntry 1 }

gamQosConfigPsfpGclGclId OBJECT-TYPE
    SYNTAX      Integer32 (0..2147483647)
    MAX-ACCESS  accessible-for-notify
    STATUS      current
    DESCRIPTION
        "GCL Id.
         
         
         
         This object is only available if the capability object
         'gamQosCapabilitiesHasPsfp' is True."
    ::= { gamQosConfigPsfpGclEntry 2 }

gamQosConfigPsfpGclGateState OBJECT-TYPE
    SYNTAX      TruthValue
    MAX-ACCESS  read-write
    STATUS      current
    DESCRIPTION
        "The GateState parameter specifies a desired state,
         
         open (true) or closed (false), for the stream gate.
         
         
         
         This object is only available if the capability object
         'gamQosCapabilitiesHasPsfp' is True."
    ::= { gamQosConfigPsfpGclEntry 3 }

gamQosConfigPsfpGclIPV OBJECT-TYPE
    SYNTAX      GAMInteger8
    MAX-ACCESS  read-write
    STATUS      current
    DESCRIPTION
        "An IPV is encoded as a signed integer.
         
         A negative denotes the null value;
         
         zero or positive values denote internal priority values.
         
         
         
         This object is only available if the capability object
         'gamQosCapabilitiesHasPsfp' is True."
    ::= { gamQosConfigPsfpGclEntry 4 }

gamQosConfigPsfpGclTimeInterval OBJECT-TYPE
    SYNTAX      Unsigned32
    MAX-ACCESS  read-write
    STATUS      current
    DESCRIPTION
        "A TimeInterval is encoded in 4 octets as a 32-bit
         
         unsigned integer, representing a number of nanoseconds.
         
         
         
         This object is only available if the capability object
         'gamQosCapabilitiesHasPsfp' is True."
    ::= { gamQosConfigPsfpGclEntry 5 }

gamQosConfigPsfpGclOctetMax OBJECT-TYPE
    SYNTAX      Unsigned32
    MAX-ACCESS  read-write
    STATUS      current
    DESCRIPTION
        "The maximum number of octets that are permitted to pass
         
         the gate during the specified TimeInterval.
         
         If zero, there is no maximum.
         
         
         
         This object is only available if the capability object
         'gamQosCapabilitiesHasPsfp' is True."
    ::= { gamQosConfigPsfpGclEntry 6 }

gamQosConfigPsfpSgiTable OBJECT-TYPE
    SYNTAX      SEQUENCE OF GAMQosConfigPsfpSgiEntry
    MAX-ACCESS  not-accessible
    STATUS      current
    DESCRIPTION
        "This table contains the configuration of PSFP SGI's. The index is
         SGIId.
         
         This is an optional table and is only present if qosCapabilitiesHasPsfp
         is true."
    ::= { gamQosConfigPsfp 4 }

gamQosConfigPsfpSgiEntry OBJECT-TYPE
    SYNTAX      GAMQosConfigPsfpSgiEntry
    MAX-ACCESS  not-accessible
    STATUS      current
    DESCRIPTION
        "Each row contains the configuration of a single PSFP SGI."
    INDEX       { gamQosConfigPsfpSgiSgiId }
    ::= { gamQosConfigPsfpSgiTable 1 }

GAMQosConfigPsfpSgiEntry ::= SEQUENCE {
    gamQosConfigPsfpSgiSgiId                  Integer32,
    gamQosConfigPsfpSgiGateEnabled            TruthValue,
    gamQosConfigPsfpSgiGateStates             TruthValue,
    gamQosConfigPsfpSgiListMax                GAMUnsigned8,
    gamQosConfigPsfpSgiCycleTimeNumerator     Unsigned32,
    gamQosConfigPsfpSgiCycleTimeDenominator   Unsigned32,
    gamQosConfigPsfpSgiCycleTimeExtension     Unsigned32,
    gamQosConfigPsfpSgiAdminBaseTimeSecs      Unsigned32,
    gamQosConfigPsfpSgiAdminBaseTimeNanoSecs  Unsigned32,
    gamQosConfigPsfpSgiAdminIPV               GAMInteger8,
    gamQosConfigPsfpSgiConfigChange           TruthValue,
    gamQosConfigPsfpSgiBlockInvalidRxenable   TruthValue,
    gamQosConfigPsfpSgiBlockInvalidRx         TruthValue,
    gamQosConfigPsfpSgiAction                 GAMRowEditorState
}

gamQosConfigPsfpSgiSgiId OBJECT-TYPE
    SYNTAX      Integer32 (0..2147483647)
    MAX-ACCESS  accessible-for-notify
    STATUS      current
    DESCRIPTION
        "SGI Id.
         
         
         
         This object is only available if the capability object
         'gamQosCapabilitiesHasPsfp' is True."
    ::= { gamQosConfigPsfpSgiEntry 1 }

gamQosConfigPsfpSgiGateEnabled OBJECT-TYPE
    SYNTAX      TruthValue
    MAX-ACCESS  read-write
    STATUS      current
    DESCRIPTION
        "The GateEnabled parameter determines whether the stream gate is active
         (true) or inactive (false).
         
         This object is only available if the capability object
         'gamQosCapabilitiesHasPsfp' is True."
    ::= { gamQosConfigPsfpSgiEntry 2 }

gamQosConfigPsfpSgiGateStates OBJECT-TYPE
    SYNTAX      TruthValue
    MAX-ACCESS  read-write
    STATUS      current
    DESCRIPTION
        "The administrative value of the GateStates parameter for the stream
         gate. A value of false indicates closed; a value of true indicates
         open.
         
         This object is only available if the capability object
         'gamQosCapabilitiesHasPsfp' is True."
    ::= { gamQosConfigPsfpSgiEntry 3 }

gamQosConfigPsfpSgiListMax OBJECT-TYPE
    SYNTAX      GAMUnsigned8
    MAX-ACCESS  read-write
    STATUS      current
    DESCRIPTION
        "The administrative value of the ListMax parameter for the gate. The
         integer value indicates the number of entries (TLVs) in the
         AdminControlList.
         
         This object is only available if the capability object
         'gamQosCapabilitiesHasPsfp' is True."
    ::= { gamQosConfigPsfpSgiEntry 4 }

gamQosConfigPsfpSgiCycleTimeNumerator OBJECT-TYPE
    SYNTAX      Unsigned32
    MAX-ACCESS  read-write
    STATUS      current
    DESCRIPTION
        "The administrative value of the numerator of the CycleTime parameter
         for the gate. The numerator and denominator together represent the
         cycle time as a rational number of seconds.
         
         This object is only available if the capability object
         'gamQosCapabilitiesHasPsfp' is True."
    ::= { gamQosConfigPsfpSgiEntry 5 }

gamQosConfigPsfpSgiCycleTimeDenominator OBJECT-TYPE
    SYNTAX      Unsigned32
    MAX-ACCESS  read-write
    STATUS      current
    DESCRIPTION
        "The administrative value of the denominator of the CycleTime parameter
         for the gate. The numerator and denominator together represent the
         cycle time as a rational number of seconds.
         
         This object is only available if the capability object
         'gamQosCapabilitiesHasPsfp' is True."
    ::= { gamQosConfigPsfpSgiEntry 6 }

gamQosConfigPsfpSgiCycleTimeExtension OBJECT-TYPE
    SYNTAX      Unsigned32
    MAX-ACCESS  read-write
    STATUS      current
    DESCRIPTION
        "The administrative value of the CycleTimeExtension parameter for the
         gate. The value is an unsigned integer number of nanoseconds.
         
         This object is only available if the capability object
         'gamQosCapabilitiesHasPsfp' is True."
    ::= { gamQosConfigPsfpSgiEntry 7 }

gamQosConfigPsfpSgiAdminBaseTimeSecs OBJECT-TYPE
    SYNTAX      Unsigned32
    MAX-ACCESS  read-write
    STATUS      current
    DESCRIPTION
        "The administrative value of the BaseTime parameter for the gateThe
         value is a representation of a PTPtime value, consisting of aThe value
         is a representation of a PTPtime value, consisting of ananoseconds.
         
         This object is only available if the capability object
         'gamQosCapabilitiesHasPsfp' is True."
    ::= { gamQosConfigPsfpSgiEntry 8 }

gamQosConfigPsfpSgiAdminBaseTimeNanoSecs OBJECT-TYPE
    SYNTAX      Unsigned32
    MAX-ACCESS  read-write
    STATUS      current
    DESCRIPTION
        "The administrative value of the BaseTime parameter for the gateThe
         value is a representation of a PTPtime value, consisting of aThe value
         is a representation of a PTPtime value, consisting of ananoseconds.
         
         This object is only available if the capability object
         'gamQosCapabilitiesHasPsfp' is True."
    ::= { gamQosConfigPsfpSgiEntry 9 }

gamQosConfigPsfpSgiAdminIPV OBJECT-TYPE
    SYNTAX      GAMInteger8
    MAX-ACCESS  read-write
    STATUS      current
    DESCRIPTION
        "The administrative value of the IPV parameter for the gate. A value of
         -1 denotes the null value; zero or positive values denote internal
         priority values.
         
         This object is only available if the capability object
         'gamQosCapabilitiesHasPsfp' is True."
    ::= { gamQosConfigPsfpSgiEntry 10 }

gamQosConfigPsfpSgiConfigChange OBJECT-TYPE
    SYNTAX      TruthValue
    MAX-ACCESS  read-write
    STATUS      current
    DESCRIPTION
        "The ConfigChange parameter signals the start of a configuration change
         when it is set to TRUE. This should only be done when the various
         administrative parameters are all set to appropriate values.
         
         This object is only available if the capability object
         'gamQosCapabilitiesHasPsfp' is True."
    ::= { gamQosConfigPsfpSgiEntry 11 }

gamQosConfigPsfpSgiBlockInvalidRxenable OBJECT-TYPE
    SYNTAX      TruthValue
    MAX-ACCESS  read-write
    STATUS      current
    DESCRIPTION
        "The GateClosedDueToInvalidRxEnable object contains a Boolean value that
         indicates whether the GateClosedDueToInvalidRx function is enabled
         (TRUE) or disabled (FALSE).
         
         This object is only available if the capability object
         'gamQosCapabilitiesHasPsfp' is True."
    ::= { gamQosConfigPsfpSgiEntry 12 }

gamQosConfigPsfpSgiBlockInvalidRx OBJECT-TYPE
    SYNTAX      TruthValue
    MAX-ACCESS  read-write
    STATUS      current
    DESCRIPTION
        "The GateClosedDueToInvalidRx object contains a Booleanvalue that
         indicates whether, if the GateClosedDueToInvalidRxfunction is enabled,
         all frames are to be discarded (TRUE) or not (FALSE).
         
         This object is only available if the capability object
         'gamQosCapabilitiesHasPsfp' is True."
    ::= { gamQosConfigPsfpSgiEntry 13 }

gamQosConfigPsfpSgiAction OBJECT-TYPE
    SYNTAX      GAMRowEditorState
    MAX-ACCESS  read-write
    STATUS      current
    DESCRIPTION
        "Action
         
         This object is only available if the capability object
         'gamQosCapabilitiesHasPsfp' is True."
    ::= { gamQosConfigPsfpSgiEntry 10000 }

gamQosConfigPsfpSgiTableRowEditor OBJECT IDENTIFIER
    ::= { gamQosConfigPsfp 5 }

gamQosConfigPsfpSgiTableRowEditorSgiId OBJECT-TYPE
    SYNTAX      Integer32 (0..2147483647)
    MAX-ACCESS  read-write
    STATUS      current
    DESCRIPTION
        "SGI Id.
         
         
         
         This object is only available if the capability object
         'gamQosCapabilitiesHasPsfp' is True."
    ::= { gamQosConfigPsfpSgiTableRowEditor 1 }

gamQosConfigPsfpSgiTableRowEditorGateEnabled OBJECT-TYPE
    SYNTAX      TruthValue
    MAX-ACCESS  read-write
    STATUS      current
    DESCRIPTION
        "The GateEnabled parameter determines whether the stream gate is active
         (true) or inactive (false).
         
         This object is only available if the capability object
         'gamQosCapabilitiesHasPsfp' is True."
    ::= { gamQosConfigPsfpSgiTableRowEditor 2 }

gamQosConfigPsfpSgiTableRowEditorGateStates OBJECT-TYPE
    SYNTAX      TruthValue
    MAX-ACCESS  read-write
    STATUS      current
    DESCRIPTION
        "The administrative value of the GateStates parameter for the stream
         gate. A value of false indicates closed; a value of true indicates
         open.
         
         This object is only available if the capability object
         'gamQosCapabilitiesHasPsfp' is True."
    ::= { gamQosConfigPsfpSgiTableRowEditor 3 }

gamQosConfigPsfpSgiTableRowEditorListMax OBJECT-TYPE
    SYNTAX      GAMUnsigned8
    MAX-ACCESS  read-write
    STATUS      current
    DESCRIPTION
        "The administrative value of the ListMax parameter for the gate. The
         integer value indicates the number of entries (TLVs) in the
         AdminControlList.
         
         This object is only available if the capability object
         'gamQosCapabilitiesHasPsfp' is True."
    ::= { gamQosConfigPsfpSgiTableRowEditor 4 }

gamQosConfigPsfpSgiTableRowEditorCycleTimeNumerator OBJECT-TYPE
    SYNTAX      Unsigned32
    MAX-ACCESS  read-write
    STATUS      current
    DESCRIPTION
        "The administrative value of the numerator of the CycleTime parameter
         for the gate. The numerator and denominator together represent the
         cycle time as a rational number of seconds.
         
         This object is only available if the capability object
         'gamQosCapabilitiesHasPsfp' is True."
    ::= { gamQosConfigPsfpSgiTableRowEditor 5 }

gamQosConfigPsfpSgiTableRowEditorCycleTimeDenominator OBJECT-TYPE
    SYNTAX      Unsigned32
    MAX-ACCESS  read-write
    STATUS      current
    DESCRIPTION
        "The administrative value of the denominator of the CycleTime parameter
         for the gate. The numerator and denominator together represent the
         cycle time as a rational number of seconds.
         
         This object is only available if the capability object
         'gamQosCapabilitiesHasPsfp' is True."
    ::= { gamQosConfigPsfpSgiTableRowEditor 6 }

gamQosConfigPsfpSgiTableRowEditorCycleTimeExtension OBJECT-TYPE
    SYNTAX      Unsigned32
    MAX-ACCESS  read-write
    STATUS      current
    DESCRIPTION
        "The administrative value of the CycleTimeExtension parameter for the
         gate. The value is an unsigned integer number of nanoseconds.
         
         This object is only available if the capability object
         'gamQosCapabilitiesHasPsfp' is True."
    ::= { gamQosConfigPsfpSgiTableRowEditor 7 }

gamQosConfigPsfpSgiTableRowEditorAdminBaseTimeSecs OBJECT-TYPE
    SYNTAX      Unsigned32
    MAX-ACCESS  read-write
    STATUS      current
    DESCRIPTION
        "The administrative value of the BaseTime parameter for the gateThe
         value is a representation of a PTPtime value, consisting of aThe value
         is a representation of a PTPtime value, consisting of ananoseconds.
         
         This object is only available if the capability object
         'gamQosCapabilitiesHasPsfp' is True."
    ::= { gamQosConfigPsfpSgiTableRowEditor 8 }

gamQosConfigPsfpSgiTableRowEditorAdminBaseTimeNanoSecs OBJECT-TYPE
    SYNTAX      Unsigned32
    MAX-ACCESS  read-write
    STATUS      current
    DESCRIPTION
        "The administrative value of the BaseTime parameter for the gateThe
         value is a representation of a PTPtime value, consisting of aThe value
         is a representation of a PTPtime value, consisting of ananoseconds.
         
         This object is only available if the capability object
         'gamQosCapabilitiesHasPsfp' is True."
    ::= { gamQosConfigPsfpSgiTableRowEditor 9 }

gamQosConfigPsfpSgiTableRowEditorAdminIPV OBJECT-TYPE
    SYNTAX      GAMInteger8
    MAX-ACCESS  read-write
    STATUS      current
    DESCRIPTION
        "The administrative value of the IPV parameter for the gate. A value of
         -1 denotes the null value; zero or positive values denote internal
         priority values.
         
         This object is only available if the capability object
         'gamQosCapabilitiesHasPsfp' is True."
    ::= { gamQosConfigPsfpSgiTableRowEditor 10 }

gamQosConfigPsfpSgiTableRowEditorConfigChange OBJECT-TYPE
    SYNTAX      TruthValue
    MAX-ACCESS  read-write
    STATUS      current
    DESCRIPTION
        "The ConfigChange parameter signals the start of a configuration change
         when it is set to TRUE. This should only be done when the various
         administrative parameters are all set to appropriate values.
         
         This object is only available if the capability object
         'gamQosCapabilitiesHasPsfp' is True."
    ::= { gamQosConfigPsfpSgiTableRowEditor 11 }

gamQosConfigPsfpSgiTableRowEditorBlockInvalidRxenable OBJECT-TYPE
    SYNTAX      TruthValue
    MAX-ACCESS  read-write
    STATUS      current
    DESCRIPTION
        "The GateClosedDueToInvalidRxEnable object contains a Boolean value that
         indicates whether the GateClosedDueToInvalidRx function is enabled
         (TRUE) or disabled (FALSE).
         
         This object is only available if the capability object
         'gamQosCapabilitiesHasPsfp' is True."
    ::= { gamQosConfigPsfpSgiTableRowEditor 12 }

gamQosConfigPsfpSgiTableRowEditorBlockInvalidRx OBJECT-TYPE
    SYNTAX      TruthValue
    MAX-ACCESS  read-write
    STATUS      current
    DESCRIPTION
        "The GateClosedDueToInvalidRx object contains a Booleanvalue that
         indicates whether, if the GateClosedDueToInvalidRxfunction is enabled,
         all frames are to be discarded (TRUE) or not (FALSE).
         
         This object is only available if the capability object
         'gamQosCapabilitiesHasPsfp' is True."
    ::= { gamQosConfigPsfpSgiTableRowEditor 13 }

gamQosConfigPsfpSgiTableRowEditorAction OBJECT-TYPE
    SYNTAX      GAMRowEditorState
    MAX-ACCESS  read-write
    STATUS      current
    DESCRIPTION
        "Action
         
         This object is only available if the capability object
         'gamQosCapabilitiesHasPsfp' is True."
    ::= { gamQosConfigPsfpSgiTableRowEditor 10000 }

gamQosConfigPsfpFmiTable OBJECT-TYPE
    SYNTAX      SEQUENCE OF GAMQosConfigPsfpFmiEntry
    MAX-ACCESS  not-accessible
    STATUS      current
    DESCRIPTION
        "This table contains the configuration of PSFP FMI's. The index is
         FMIId.
         
         This is an optional table and is only present if qosCapabilitiesHasPsfp
         is true."
    ::= { gamQosConfigPsfp 6 }

gamQosConfigPsfpFmiEntry OBJECT-TYPE
    SYNTAX      GAMQosConfigPsfpFmiEntry
    MAX-ACCESS  not-accessible
    STATUS      current
    DESCRIPTION
        "Each row contains the configuration of a single PSFP FMI."
    INDEX       { gamQosConfigPsfpFmiFmiId }
    ::= { gamQosConfigPsfpFmiTable 1 }

GAMQosConfigPsfpFmiEntry ::= SEQUENCE {
    gamQosConfigPsfpFmiFmiId                  Integer32,
    gamQosConfigPsfpFmiFlowMeterCIR           Unsigned32,
    gamQosConfigPsfpFmiFlowMeterCBS           Unsigned32,
    gamQosConfigPsfpFmiFlowMeterEIR           Unsigned32,
    gamQosConfigPsfpFmiFlowMeterEBS           Unsigned32,
    gamQosConfigPsfpFmiFlowMeterCF            TruthValue,
    gamQosConfigPsfpFmiFlowMeterCM            TruthValue,
    gamQosConfigPsfpFmiFlowMeterDropOnYellow  TruthValue,
    gamQosConfigPsfpFmiMarkRedEnable          TruthValue,
    gamQosConfigPsfpFmiMarkRed                TruthValue,
    gamQosConfigPsfpFmiAction                 GAMRowEditorState
}

gamQosConfigPsfpFmiFmiId OBJECT-TYPE
    SYNTAX      Integer32 (0..2147483647)
    MAX-ACCESS  accessible-for-notify
    STATUS      current
    DESCRIPTION
        "FMI Id.
         
         
         
         This object is only available if the capability object
         'gamQosCapabilitiesHasPsfp' is True."
    ::= { gamQosConfigPsfpFmiEntry 1 }

gamQosConfigPsfpFmiFlowMeterCIR OBJECT-TYPE
    SYNTAX      Unsigned32
    MAX-ACCESS  read-write
    STATUS      current
    DESCRIPTION
        "The FlowMeterCIR parameter contains an integer value that represents
         the CIR value for the flow meter, in kbit/s.
         
         This object is only available if the capability object
         'gamQosCapabilitiesHasPsfp' is True."
    ::= { gamQosConfigPsfpFmiEntry 2 }

gamQosConfigPsfpFmiFlowMeterCBS OBJECT-TYPE
    SYNTAX      Unsigned32
    MAX-ACCESS  read-write
    STATUS      current
    DESCRIPTION
        "The FlowMeterCBS parameter contains an integer value that represents
         the CBS value for the flow meter, in octets.
         
         This object is only available if the capability object
         'gamQosCapabilitiesHasPsfp' is True."
    ::= { gamQosConfigPsfpFmiEntry 3 }

gamQosConfigPsfpFmiFlowMeterEIR OBJECT-TYPE
    SYNTAX      Unsigned32
    MAX-ACCESS  read-write
    STATUS      current
    DESCRIPTION
        "The FlowMeterEIR parameter contains an integer value that represents
         the EIR value for the flow meter, in kbit/s.
         
         This object is only available if the capability object
         'gamQosCapabilitiesHasPsfp' is True."
    ::= { gamQosConfigPsfpFmiEntry 4 }

gamQosConfigPsfpFmiFlowMeterEBS OBJECT-TYPE
    SYNTAX      Unsigned32
    MAX-ACCESS  read-write
    STATUS      current
    DESCRIPTION
        "The FlowMeterEBS parameter contains an integer value that represents
         the EBS value for the flow meter, in octets.
         
         This object is only available if the capability object
         'gamQosCapabilitiesHasPsfp' is True."
    ::= { gamQosConfigPsfpFmiEntry 5 }

gamQosConfigPsfpFmiFlowMeterCF OBJECT-TYPE
    SYNTAX      TruthValue
    MAX-ACCESS  read-write
    STATUS      current
    DESCRIPTION
        "The FlowMeterCF parameter contains a Boolean value that represents the
         CF value for the flow meter, as a Boolean value indicating no coupling
         (FALSE) or coupling (TRUE).
         
         This object is only available if the capability object
         'gamQosCapabilitiesHasPsfp' is True."
    ::= { gamQosConfigPsfpFmiEntry 6 }

gamQosConfigPsfpFmiFlowMeterCM OBJECT-TYPE
    SYNTAX      TruthValue
    MAX-ACCESS  read-write
    STATUS      current
    DESCRIPTION
        "The FlowMeterCM parameter contains a Boolean value that represents the
         CM value for the flow meter, as a Boolean value indicating colorBlind
         (FALSE) or colorAware (TRUE).
         
         This object is only available if the capability object
         'gamQosCapabilitiesHasPsfp' is True."
    ::= { gamQosConfigPsfpFmiEntry 7 }

gamQosConfigPsfpFmiFlowMeterDropOnYellow OBJECT-TYPE
    SYNTAX      TruthValue
    MAX-ACCESS  read-write
    STATUS      current
    DESCRIPTION
        "The FlowMeterDropOnYellow parameter contains a Boolean value that
         indicates whether yellow frames are dropped (TRUE) or have
         drop_eligible set to TRUE (FALSE).
         
         This object is only available if the capability object
         'gamQosCapabilitiesHasPsfp' is True."
    ::= { gamQosConfigPsfpFmiEntry 8 }

gamQosConfigPsfpFmiMarkRedEnable OBJECT-TYPE
    SYNTAX      TruthValue
    MAX-ACCESS  read-write
    STATUS      current
    DESCRIPTION
        "The FlowMeterMarkAllFramesRedEnable parameter contains a Boolean value
         that indicates whether the MarkAllFramesRed function is enabled (TRUE)
         or disabled (FALSE).
         
         This object is only available if the capability object
         'gamQosCapabilitiesHasPsfp' is True."
    ::= { gamQosConfigPsfpFmiEntry 9 }

gamQosConfigPsfpFmiMarkRed OBJECT-TYPE
    SYNTAX      TruthValue
    MAX-ACCESS  read-write
    STATUS      current
    DESCRIPTION
        "The FlowMeterMarkAllFramesRed parameter contains a Boolean value that
         indicates whether if the MarkAllFramesRed function is enabled, all
         frames are to be discarded (TRUE) or not (FALSE).
         
         This object is only available if the capability object
         'gamQosCapabilitiesHasPsfp' is True."
    ::= { gamQosConfigPsfpFmiEntry 10 }

gamQosConfigPsfpFmiAction OBJECT-TYPE
    SYNTAX      GAMRowEditorState
    MAX-ACCESS  read-write
    STATUS      current
    DESCRIPTION
        "Action
         
         This object is only available if the capability object
         'gamQosCapabilitiesHasPsfp' is True."
    ::= { gamQosConfigPsfpFmiEntry 10000 }

gamQosConfigPsfpFmiTableRowEditor OBJECT IDENTIFIER
    ::= { gamQosConfigPsfp 7 }

gamQosConfigPsfpFmiTableRowEditorFmiId OBJECT-TYPE
    SYNTAX      Integer32 (0..2147483647)
    MAX-ACCESS  read-write
    STATUS      current
    DESCRIPTION
        "FMI Id.
         
         
         
         This object is only available if the capability object
         'gamQosCapabilitiesHasPsfp' is True."
    ::= { gamQosConfigPsfpFmiTableRowEditor 1 }

gamQosConfigPsfpFmiTableRowEditorFlowMeterCIR OBJECT-TYPE
    SYNTAX      Unsigned32
    MAX-ACCESS  read-write
    STATUS      current
    DESCRIPTION
        "The FlowMeterCIR parameter contains an integer value that represents
         the CIR value for the flow meter, in kbit/s.
         
         This object is only available if the capability object
         'gamQosCapabilitiesHasPsfp' is True."
    ::= { gamQosConfigPsfpFmiTableRowEditor 2 }

gamQosConfigPsfpFmiTableRowEditorFlowMeterCBS OBJECT-TYPE
    SYNTAX      Unsigned32
    MAX-ACCESS  read-write
    STATUS      current
    DESCRIPTION
        "The FlowMeterCBS parameter contains an integer value that represents
         the CBS value for the flow meter, in octets.
         
         This object is only available if the capability object
         'gamQosCapabilitiesHasPsfp' is True."
    ::= { gamQosConfigPsfpFmiTableRowEditor 3 }

gamQosConfigPsfpFmiTableRowEditorFlowMeterEIR OBJECT-TYPE
    SYNTAX      Unsigned32
    MAX-ACCESS  read-write
    STATUS      current
    DESCRIPTION
        "The FlowMeterEIR parameter contains an integer value that represents
         the EIR value for the flow meter, in kbit/s.
         
         This object is only available if the capability object
         'gamQosCapabilitiesHasPsfp' is True."
    ::= { gamQosConfigPsfpFmiTableRowEditor 4 }

gamQosConfigPsfpFmiTableRowEditorFlowMeterEBS OBJECT-TYPE
    SYNTAX      Unsigned32
    MAX-ACCESS  read-write
    STATUS      current
    DESCRIPTION
        "The FlowMeterEBS parameter contains an integer value that represents
         the EBS value for the flow meter, in octets.
         
         This object is only available if the capability object
         'gamQosCapabilitiesHasPsfp' is True."
    ::= { gamQosConfigPsfpFmiTableRowEditor 5 }

gamQosConfigPsfpFmiTableRowEditorFlowMeterCF OBJECT-TYPE
    SYNTAX      TruthValue
    MAX-ACCESS  read-write
    STATUS      current
    DESCRIPTION
        "The FlowMeterCF parameter contains a Boolean value that represents the
         CF value for the flow meter, as a Boolean value indicating no coupling
         (FALSE) or coupling (TRUE).
         
         This object is only available if the capability object
         'gamQosCapabilitiesHasPsfp' is True."
    ::= { gamQosConfigPsfpFmiTableRowEditor 6 }

gamQosConfigPsfpFmiTableRowEditorFlowMeterCM OBJECT-TYPE
    SYNTAX      TruthValue
    MAX-ACCESS  read-write
    STATUS      current
    DESCRIPTION
        "The FlowMeterCM parameter contains a Boolean value that represents the
         CM value for the flow meter, as a Boolean value indicating colorBlind
         (FALSE) or colorAware (TRUE).
         
         This object is only available if the capability object
         'gamQosCapabilitiesHasPsfp' is True."
    ::= { gamQosConfigPsfpFmiTableRowEditor 7 }

gamQosConfigPsfpFmiTableRowEditorFlowMeterDropOnYellow OBJECT-TYPE
    SYNTAX      TruthValue
    MAX-ACCESS  read-write
    STATUS      current
    DESCRIPTION
        "The FlowMeterDropOnYellow parameter contains a Boolean value that
         indicates whether yellow frames are dropped (TRUE) or have
         drop_eligible set to TRUE (FALSE).
         
         This object is only available if the capability object
         'gamQosCapabilitiesHasPsfp' is True."
    ::= { gamQosConfigPsfpFmiTableRowEditor 8 }

gamQosConfigPsfpFmiTableRowEditorMarkRedEnable OBJECT-TYPE
    SYNTAX      TruthValue
    MAX-ACCESS  read-write
    STATUS      current
    DESCRIPTION
        "The FlowMeterMarkAllFramesRedEnable parameter contains a Boolean value
         that indicates whether the MarkAllFramesRed function is enabled (TRUE)
         or disabled (FALSE).
         
         This object is only available if the capability object
         'gamQosCapabilitiesHasPsfp' is True."
    ::= { gamQosConfigPsfpFmiTableRowEditor 9 }

gamQosConfigPsfpFmiTableRowEditorMarkRed OBJECT-TYPE
    SYNTAX      TruthValue
    MAX-ACCESS  read-write
    STATUS      current
    DESCRIPTION
        "The FlowMeterMarkAllFramesRed parameter contains a Boolean value that
         indicates whether if the MarkAllFramesRed function is enabled, all
         frames are to be discarded (TRUE) or not (FALSE).
         
         This object is only available if the capability object
         'gamQosCapabilitiesHasPsfp' is True."
    ::= { gamQosConfigPsfpFmiTableRowEditor 10 }

gamQosConfigPsfpFmiTableRowEditorAction OBJECT-TYPE
    SYNTAX      GAMRowEditorState
    MAX-ACCESS  read-write
    STATUS      current
    DESCRIPTION
        "Action
         
         This object is only available if the capability object
         'gamQosCapabilitiesHasPsfp' is True."
    ::= { gamQosConfigPsfpFmiTableRowEditor 10000 }

gamQosStatus OBJECT IDENTIFIER
    ::= { gamQosMibObjects 3 }

gamQosStatusInterface OBJECT IDENTIFIER
    ::= { gamQosStatus 2 }

gamQosStatusInterfaceTable OBJECT-TYPE
    SYNTAX      SEQUENCE OF GAMQosStatusInterfaceEntry
    MAX-ACCESS  not-accessible
    STATUS      current
    DESCRIPTION
        "This table provides QoS status for QoS manageable interfaces"
    ::= { gamQosStatusInterface 1 }

gamQosStatusInterfaceEntry OBJECT-TYPE
    SYNTAX      GAMQosStatusInterfaceEntry
    MAX-ACCESS  not-accessible
    STATUS      current
    DESCRIPTION
        "Each row contains the status for a specific interface"
    INDEX       { gamQosStatusInterfaceIfIndex }
    ::= { gamQosStatusInterfaceTable 1 }

GAMQosStatusInterfaceEntry ::= SEQUENCE {
    gamQosStatusInterfaceIfIndex  GAMInterfaceIndex,
    gamQosStatusInterfaceCos      Unsigned32
}

gamQosStatusInterfaceIfIndex OBJECT-TYPE
    SYNTAX      GAMInterfaceIndex
    MAX-ACCESS  accessible-for-notify
    STATUS      current
    DESCRIPTION
        "Logical interface index."
    ::= { gamQosStatusInterfaceEntry 1 }

gamQosStatusInterfaceCos OBJECT-TYPE
    SYNTAX      Unsigned32
    MAX-ACCESS  read-only
    STATUS      current
    DESCRIPTION
        "Some subsystems are allowed to modify the default CoS value for an
         interface. This object shows the actual default CoS value a packet is
         classified to."
    ::= { gamQosStatusInterfaceEntry 2 }

gamQosStatusInterfaceSchedulerTable OBJECT-TYPE
    SYNTAX      SEQUENCE OF GAMQosStatusInterfaceSchedulerEntry
    MAX-ACCESS  not-accessible
    STATUS      current
    DESCRIPTION
        "This table contains the mapping of (interface, queue) to weight values.
         
         The mappings given by this table are the 'real' weights in percent as
         used by the hardware."
    ::= { gamQosStatusInterface 2 }

gamQosStatusInterfaceSchedulerEntry OBJECT-TYPE
    SYNTAX      GAMQosStatusInterfaceSchedulerEntry
    MAX-ACCESS  not-accessible
    STATUS      current
    DESCRIPTION
        "Each row contains the scheduler status for a specific queue."
    INDEX       { gamQosStatusInterfaceSchedulerIfIndex,
                  gamQosStatusInterfaceSchedulerQueue }
    ::= { gamQosStatusInterfaceSchedulerTable 1 }

GAMQosStatusInterfaceSchedulerEntry ::= SEQUENCE {
    gamQosStatusInterfaceSchedulerIfIndex  GAMInterfaceIndex,
    gamQosStatusInterfaceSchedulerQueue    Integer32,
    gamQosStatusInterfaceSchedulerWeight   GAMPercent
}

gamQosStatusInterfaceSchedulerIfIndex OBJECT-TYPE
    SYNTAX      GAMInterfaceIndex
    MAX-ACCESS  accessible-for-notify
    STATUS      current
    DESCRIPTION
        "Logical interface index."
    ::= { gamQosStatusInterfaceSchedulerEntry 1 }

gamQosStatusInterfaceSchedulerQueue OBJECT-TYPE
    SYNTAX      Integer32 (0..7)
    MAX-ACCESS  accessible-for-notify
    STATUS      current
    DESCRIPTION
        "Queue index."
    ::= { gamQosStatusInterfaceSchedulerEntry 2 }

gamQosStatusInterfaceSchedulerWeight OBJECT-TYPE
    SYNTAX      GAMPercent
    MAX-ACCESS  read-only
    STATUS      current
    DESCRIPTION
        "The actual weight for this queue."
    ::= { gamQosStatusInterfaceSchedulerEntry 3 }

gamQosStatusInterfaceQbvGclOprTable OBJECT-TYPE
    SYNTAX      SEQUENCE OF GAMQosStatusInterfaceQbvGclOprEntry
    MAX-ACCESS  not-accessible
    STATUS      current
    DESCRIPTION
        "A table containing the operational entries/TLVs of the GCL, as defined
         in IEEE 802.1Qbv"
    ::= { gamQosStatusInterface 3 }

gamQosStatusInterfaceQbvGclOprEntry OBJECT-TYPE
    SYNTAX      GAMQosStatusInterfaceQbvGclOprEntry
    MAX-ACCESS  not-accessible
    STATUS      current
    DESCRIPTION
        "Each row contains single GCL entry with a unique gcl_index"
    INDEX       { gamQosStatusInterfaceQbvGclOprIfIndex,
                  gamQosStatusInterfaceQbvGclOprGclIndex }
    ::= { gamQosStatusInterfaceQbvGclOprTable 1 }

GAMQosStatusInterfaceQbvGclOprEntry ::= SEQUENCE {
    gamQosStatusInterfaceQbvGclOprIfIndex       GAMInterfaceIndex,
    gamQosStatusInterfaceQbvGclOprGclIndex      Integer32,
    gamQosStatusInterfaceQbvGclOprGateState     OCTET STRING,
    gamQosStatusInterfaceQbvGclOprTimeInterval  Unsigned32
}

gamQosStatusInterfaceQbvGclOprIfIndex OBJECT-TYPE
    SYNTAX      GAMInterfaceIndex
    MAX-ACCESS  accessible-for-notify
    STATUS      current
    DESCRIPTION
        "Logical interface index.
         
         This object is only available if the capability object
         'gamQosCapabilitiesHasQbv' is True."
    ::= { gamQosStatusInterfaceQbvGclOprEntry 1 }

gamQosStatusInterfaceQbvGclOprGclIndex OBJECT-TYPE
    SYNTAX      Integer32 (0..63)
    MAX-ACCESS  accessible-for-notify
    STATUS      current
    DESCRIPTION
        "Gate control list index.
         
         This object is only available if the capability object
         'gamQosCapabilitiesHasQbv' is True."
    ::= { gamQosStatusInterfaceQbvGclOprEntry 2 }

gamQosStatusInterfaceQbvGclOprGateState OBJECT-TYPE
    SYNTAX      OCTET STRING (SIZE(1))
    MAX-ACCESS  read-only
    STATUS      current
    DESCRIPTION
        "A GateState parameter is encoded in a single octet.
         
         The bits of the octet represent the gate states for the
         
         corresponding traffic classes;the MS bit corresponds to
         
         traffic class 7, the LS bit to traffic class 0.
         
         A bit value of 0 indicates closed;a
         
         bit value of 1 indicates open.
         
         
         
         This object is only available if the capability object
         'gamQosCapabilitiesHasQbv' is True."
    ::= { gamQosStatusInterfaceQbvGclOprEntry 3 }

gamQosStatusInterfaceQbvGclOprTimeInterval OBJECT-TYPE
    SYNTAX      Unsigned32
    MAX-ACCESS  read-only
    STATUS      current
    DESCRIPTION
        "A TimeInterval is encoded in 4 octets as a 32-bit
         
         unsigned integer, representing
         
         a number of nanoseconds. The first octet encodes the
         
         most significant 8 bits of the integer, and the fourth
         
         octet encodes the least significant 8 bits.
         
         
         
         This object is only available if the capability object
         'gamQosCapabilitiesHasQbv' is True."
    ::= { gamQosStatusInterfaceQbvGclOprEntry 4 }

gamQosStatusInterfaceQbvOprStatusTable OBJECT-TYPE
    SYNTAX      SEQUENCE OF GAMQosStatusInterfaceQbvOprStatusEntry
    MAX-ACCESS  not-accessible
    STATUS      current
    DESCRIPTION
        "A table that contains the per-port operational value of parameters for
         traffic scheduling."
    ::= { gamQosStatusInterface 4 }

gamQosStatusInterfaceQbvOprStatusEntry OBJECT-TYPE
    SYNTAX      GAMQosStatusInterfaceQbvOprStatusEntry
    MAX-ACCESS  not-accessible
    STATUS      current
    DESCRIPTION
        "A list of objects that contains the operational value of parameters for
         a port."
    INDEX       { gamQosStatusInterfaceQbvOprStatusIfIndex }
    ::= { gamQosStatusInterfaceQbvOprStatusTable 1 }

GAMQosStatusInterfaceQbvOprStatusEntry ::= SEQUENCE {
    gamQosStatusInterfaceQbvOprStatusIfIndex                   GAMInterfaceIndex,
    gamQosStatusInterfaceQbvOprStatusOperGateStates            OCTET STRING,
    gamQosStatusInterfaceQbvOprStatusOperControlListLength     Unsigned32,
    gamQosStatusInterfaceQbvOprStatusOperCycleTimeNumerator    Unsigned32,
    gamQosStatusInterfaceQbvOprStatusOperCycleTimeDenominator  Unsigned32,
    gamQosStatusInterfaceQbvOprStatusOperCycleTimeExtension    Unsigned32,
    gamQosStatusInterfaceQbvOprStatusOperBaseTimeSecs          Unsigned32,
    gamQosStatusInterfaceQbvOprStatusOperBaseTimeNanoSecs      Unsigned32,
    gamQosStatusInterfaceQbvOprStatusConfigChangeTime          IEEE8021STPTPtimeValue,
    gamQosStatusInterfaceQbvOprStatusTickGranularity           Unsigned32,
    gamQosStatusInterfaceQbvOprStatusCurrentTime               IEEE8021STPTPtimeValue,
    gamQosStatusInterfaceQbvOprStatusConfigPending             TruthValue,
    gamQosStatusInterfaceQbvOprStatusConfigChangeError         Counter64,
    gamQosStatusInterfaceQbvOprStatusSupportedListMax          Unsigned32
}

gamQosStatusInterfaceQbvOprStatusIfIndex OBJECT-TYPE
    SYNTAX      GAMInterfaceIndex
    MAX-ACCESS  accessible-for-notify
    STATUS      current
    DESCRIPTION
        "Logical interface index.
         
         This object is only available if the capability object
         'gamQosCapabilitiesHasQbv' is True."
    ::= { gamQosStatusInterfaceQbvOprStatusEntry 1 }

gamQosStatusInterfaceQbvOprStatusOperGateStates OBJECT-TYPE
    SYNTAX      OCTET STRING (SIZE(1))
    MAX-ACCESS  read-only
    STATUS      current
    DESCRIPTION
        "The operational value of the GateStates parameter for the Port.
         
         The bits of the octet represent the gate states for the
         
         corresponding traffic classes;the MS bit corresponds to traffic class
         7,
         
         the LS bit to traffic class 0. A bit value of 0 indicates closed;a
         
         bit value of 1 indicates open.
         
         
         
         This object is only available if the capability object
         'gamQosCapabilitiesHasQbv' is True."
    ::= { gamQosStatusInterfaceQbvOprStatusEntry 2 }

gamQosStatusInterfaceQbvOprStatusOperControlListLength OBJECT-TYPE
    SYNTAX      Unsigned32
    MAX-ACCESS  read-only
    STATUS      current
    DESCRIPTION
        "The operational value of the ListMax parameter for the Port.
         
         The integer value indicates the number of entries (TLVs) in the
         
         OperControlList.
         
         
         
         This object is only available if the capability object
         'gamQosCapabilitiesHasQbv' is True."
    ::= { gamQosStatusInterfaceQbvOprStatusEntry 3 }

gamQosStatusInterfaceQbvOprStatusOperCycleTimeNumerator OBJECT-TYPE
    SYNTAX      Unsigned32
    MAX-ACCESS  read-only
    STATUS      current
    DESCRIPTION
        "The operational value of the numerator of the
         
         CycleTime parameter for the Port.
         
         The numerator and denominator together represent the cycle
         
         time as a rational number of seconds.
         
         
         
         This object is only available if the capability object
         'gamQosCapabilitiesHasQbv' is True."
    ::= { gamQosStatusInterfaceQbvOprStatusEntry 4 }

gamQosStatusInterfaceQbvOprStatusOperCycleTimeDenominator OBJECT-TYPE
    SYNTAX      Unsigned32
    MAX-ACCESS  read-only
    STATUS      current
    DESCRIPTION
        "The operational value of the denominator of the
         
         CycleTime parameter for the Port.
         
         The numerator and denominator together represent the
         
         cycle time as a rational number of seconds.
         
         
         
         This object is only available if the capability object
         'gamQosCapabilitiesHasQbv' is True."
    ::= { gamQosStatusInterfaceQbvOprStatusEntry 5 }

gamQosStatusInterfaceQbvOprStatusOperCycleTimeExtension OBJECT-TYPE
    SYNTAX      Unsigned32
    MAX-ACCESS  read-only
    STATUS      current
    DESCRIPTION
        "The operational value of the CycleTimeExtension parameter for the Port.
         
         The value is an unsigned integer number of nanoseconds.
         
         
         
         This object is only available if the capability object
         'gamQosCapabilitiesHasQbv' is True."
    ::= { gamQosStatusInterfaceQbvOprStatusEntry 6 }

gamQosStatusInterfaceQbvOprStatusOperBaseTimeSecs OBJECT-TYPE
    SYNTAX      Unsigned32
    MAX-ACCESS  read-only
    STATUS      current
    DESCRIPTION
        "The operationsl value of the BaseTime parameter for the Port.
         
         The value is a representation of a PTPtime value,
         
         consisting of a 48-bit integer
         
         number of seconds and a 32-bit integer number of nanoseconds.
         
         
         
         This object is only available if the capability object
         'gamQosCapabilitiesHasQbv' is True."
    ::= { gamQosStatusInterfaceQbvOprStatusEntry 7 }

gamQosStatusInterfaceQbvOprStatusOperBaseTimeNanoSecs OBJECT-TYPE
    SYNTAX      Unsigned32
    MAX-ACCESS  read-only
    STATUS      current
    DESCRIPTION
        "The operationsl value of the BaseTime parameter for the Port.
         
         The value is a representation of a PTPtime value,
         
         consisting of a 48-bit integer
         
         number of seconds and a 32-bit integer number of nanoseconds.
         
         
         
         This object is only available if the capability object
         'gamQosCapabilitiesHasQbv' is True."
    ::= { gamQosStatusInterfaceQbvOprStatusEntry 8 }

gamQosStatusInterfaceQbvOprStatusConfigChangeTime OBJECT-TYPE
    SYNTAX      IEEE8021STPTPtimeValue
    MAX-ACCESS  read-only
    STATUS      current
    DESCRIPTION
        "The PTPtime at which the next config change is scheduled to occur.
         
         The value is a representation of a PTPtime value,
         
         consisting of a 48-bit integer
         
         number of seconds and a 32-bit integer number of nanoseconds.
         
         The value of this object MUST be retained across
         
         reinitializations of the management system.
         
         
         
         This object is only available if the capability object
         'gamQosCapabilitiesHasQbv' is True."
    ::= { gamQosStatusInterfaceQbvOprStatusEntry 9 }

gamQosStatusInterfaceQbvOprStatusTickGranularity OBJECT-TYPE
    SYNTAX      Unsigned32
    MAX-ACCESS  read-only
    STATUS      current
    DESCRIPTION
        "The granularity of the cycle time clock, represented as an
         
         unsigned number of tenths of nanoseconds.
         
         The value of this object MUST be retained across
         
         reinitializations of the management system.
         
         
         
         This object is only available if the capability object
         'gamQosCapabilitiesHasQbv' is True."
    ::= { gamQosStatusInterfaceQbvOprStatusEntry 10 }

gamQosStatusInterfaceQbvOprStatusCurrentTime OBJECT-TYPE
    SYNTAX      IEEE8021STPTPtimeValue
    MAX-ACCESS  read-only
    STATUS      current
    DESCRIPTION
        "The current time, in PTPtime, as maintained by the local system.
         
         The value is a representation of a PTPtime value,
         
         consisting of a 48-bit integer
         
         number of seconds and a 32-bit integer number of nanoseconds.
         
         
         
         This object is only available if the capability object
         'gamQosCapabilitiesHasQbv' is True."
    ::= { gamQosStatusInterfaceQbvOprStatusEntry 11 }

gamQosStatusInterfaceQbvOprStatusConfigPending OBJECT-TYPE
    SYNTAX      TruthValue
    MAX-ACCESS  read-only
    STATUS      current
    DESCRIPTION
        "The value of the ConfigPending state machine variable.
         
         The value is TRUE if a configuration change is in progress
         
         but has not yet completed.
         
         
         
         This object is only available if the capability object
         'gamQosCapabilitiesHasQbv' is True."
    ::= { gamQosStatusInterfaceQbvOprStatusEntry 12 }

gamQosStatusInterfaceQbvOprStatusConfigChangeError OBJECT-TYPE
    SYNTAX      Counter64
    MAX-ACCESS  read-only
    STATUS      current
    DESCRIPTION
        "A counter of the number of times that a re-configuration
         
         of the traffic schedule has been requested with the old
         
         schedule still running and the requested base time was
         
         in the past.
         
         
         
         This object is only available if the capability object
         'gamQosCapabilitiesHasQbv' is True."
    ::= { gamQosStatusInterfaceQbvOprStatusEntry 13 }

gamQosStatusInterfaceQbvOprStatusSupportedListMax OBJECT-TYPE
    SYNTAX      Unsigned32
    MAX-ACCESS  read-only
    STATUS      current
    DESCRIPTION
        "The maximum value supported by this Port of the
         
         AdminControlListLength and OperControlListLength
         
         parameters.
         
         
         
         This object is only available if the capability object
         'gamQosCapabilitiesHasQbv' is True."
    ::= { gamQosStatusInterfaceQbvOprStatusEntry 14 }

gamQosStatusInterfaceFpStatusTable OBJECT-TYPE
    SYNTAX      SEQUENCE OF GAMQosStatusInterfaceFpStatusEntry
    MAX-ACCESS  not-accessible
    STATUS      current
    DESCRIPTION
        "A table that contains the per-port frame preemption status."
    ::= { gamQosStatusInterface 5 }

gamQosStatusInterfaceFpStatusEntry OBJECT-TYPE
    SYNTAX      GAMQosStatusInterfaceFpStatusEntry
    MAX-ACCESS  not-accessible
    STATUS      current
    DESCRIPTION
        "A list of objects that contains the frame preemption status for a port."
    INDEX       { gamQosStatusInterfaceFpStatusIfIndex }
    ::= { gamQosStatusInterfaceFpStatusTable 1 }

GAMQosStatusInterfaceFpStatusEntry ::= SEQUENCE {
    gamQosStatusInterfaceFpStatusIfIndex              GAMInterfaceIndex,
    gamQosStatusInterfaceFpStatusHoldAdvance          Unsigned32,
    gamQosStatusInterfaceFpStatusReleaseAdvance       Unsigned32,
    gamQosStatusInterfaceFpStatusPreemptionActive     TruthValue,
    gamQosStatusInterfaceFpStatusHoldRequest          TruthValue,
    gamQosStatusInterfaceFpStatusStatusVerify         GAMQosMmStatusVerify,
    gamQosStatusInterfaceFpStatusLocPreemptSupported  TruthValue,
    gamQosStatusInterfaceFpStatusLocPreemptEnabled    TruthValue,
    gamQosStatusInterfaceFpStatusLocPreemptActive     TruthValue,
    gamQosStatusInterfaceFpStatusLocAddFragSize       GAMUnsigned8
}

gamQosStatusInterfaceFpStatusIfIndex OBJECT-TYPE
    SYNTAX      GAMInterfaceIndex
    MAX-ACCESS  accessible-for-notify
    STATUS      current
    DESCRIPTION
        "Logical interface index.
         
         This object is only available if the capability object
         'gamQosCapabilitiesHasQueueFramePreemption' is True."
    ::= { gamQosStatusInterfaceFpStatusEntry 1 }

gamQosStatusInterfaceFpStatusHoldAdvance OBJECT-TYPE
    SYNTAX      Unsigned32
    MAX-ACCESS  read-only
    STATUS      current
    DESCRIPTION
        "The value of the holdAdvance parameter for the port in nanoseconds.
         
         This object is only available if the capability object
         'gamQosCapabilitiesHasQueueFramePreemption' is True."
    ::= { gamQosStatusInterfaceFpStatusEntry 2 }

gamQosStatusInterfaceFpStatusReleaseAdvance OBJECT-TYPE
    SYNTAX      Unsigned32
    MAX-ACCESS  read-only
    STATUS      current
    DESCRIPTION
        "The value of the releaseAdvance parameter for the port in nanoseconds.
         
         This object is only available if the capability object
         'gamQosCapabilitiesHasQueueFramePreemption' is True."
    ::= { gamQosStatusInterfaceFpStatusEntry 3 }

gamQosStatusInterfaceFpStatusPreemptionActive OBJECT-TYPE
    SYNTAX      TruthValue
    MAX-ACCESS  read-only
    STATUS      current
    DESCRIPTION
        "The value is active (TRUE) when preemption is operationally active for
         the port, and idle (FALSE) otherwise.
         
         This object is only available if the capability object
         'gamQosCapabilitiesHasQueueFramePreemption' is True."
    ::= { gamQosStatusInterfaceFpStatusEntry 4 }

gamQosStatusInterfaceFpStatusHoldRequest OBJECT-TYPE
    SYNTAX      TruthValue
    MAX-ACCESS  read-only
    STATUS      current
    DESCRIPTION
        "The value is hold (TRUE) when the sequence of gate operations for the
         port has executed a Set-And-Hold-MAC operation, and release (FALSE)
         when the sequence of gate operations has executed a Set-And-Release-MAC
         operation.
         
         The value of this object is release (FALSE) on system initialization.
         
         This object is only available if the capability object
         'gamQosCapabilitiesHasQueueFramePreemption' is True."
    ::= { gamQosStatusInterfaceFpStatusEntry 5 }

gamQosStatusInterfaceFpStatusStatusVerify OBJECT-TYPE
    SYNTAX      GAMQosMmStatusVerify
    MAX-ACCESS  read-only
    STATUS      current
    DESCRIPTION
        "The status of the MAC Merge sublayer verification for the given device.
         
         This object is only available if the capability object
         'gamQosCapabilitiesHasQueueFramePreemption' is True."
    ::= { gamQosStatusInterfaceFpStatusEntry 6 }

gamQosStatusInterfaceFpStatusLocPreemptSupported OBJECT-TYPE
    SYNTAX      TruthValue
    MAX-ACCESS  read-only
    STATUS      current
    DESCRIPTION
        "The value is TRUE when preemption is supported on the port, and FALSE
         otherwise.
         
         This object is only available if the capability object
         'gamQosCapabilitiesHasQueueFramePreemption' is True."
    ::= { gamQosStatusInterfaceFpStatusEntry 7 }

gamQosStatusInterfaceFpStatusLocPreemptEnabled OBJECT-TYPE
    SYNTAX      TruthValue
    MAX-ACCESS  read-only
    STATUS      current
    DESCRIPTION
        "The value is TRUE when preemption is enabled on the port, and FALSE
         otherwise.
         
         This object is only available if the capability object
         'gamQosCapabilitiesHasQueueFramePreemption' is True."
    ::= { gamQosStatusInterfaceFpStatusEntry 8 }

gamQosStatusInterfaceFpStatusLocPreemptActive OBJECT-TYPE
    SYNTAX      TruthValue
    MAX-ACCESS  read-only
    STATUS      current
    DESCRIPTION
        "The value is TRUE when preemption is operationally active on the port,
         and FALSE otherwise.
         
         This object is only available if the capability object
         'gamQosCapabilitiesHasQueueFramePreemption' is True."
    ::= { gamQosStatusInterfaceFpStatusEntry 9 }

gamQosStatusInterfaceFpStatusLocAddFragSize OBJECT-TYPE
    SYNTAX      GAMUnsigned8
    MAX-ACCESS  read-only
    STATUS      current
    DESCRIPTION
        "The value of the 802.3br LocAddFragSize parameter for the port. The
         minimum size of non-final fragments supported by the receiver on the
         local port. This value is expressed in units of 64 octets of additional
         fragment length. The minimum non-final fragment size is:
         (LocAddFragSize + 1) * 64 octets.
         
         This object is only available if the capability object
         'gamQosCapabilitiesHasQueueFramePreemption' is True."
    ::= { gamQosStatusInterfaceFpStatusEntry 10 }

gamQosStatusQce OBJECT IDENTIFIER
    ::= { gamQosStatus 3 }

gamQosStatusQceTable OBJECT-TYPE
    SYNTAX      SEQUENCE OF GAMQosStatusQceEntry
    MAX-ACCESS  not-accessible
    STATUS      current
    DESCRIPTION
        "This table contains the QCE status in the hardware table.
         
         This is an optional table and is only present if qosCapabilitiesHasQce
         is true."
    ::= { gamQosStatusQce 1 }

gamQosStatusQceEntry OBJECT-TYPE
    SYNTAX      GAMQosStatusQceEntry
    MAX-ACCESS  not-accessible
    STATUS      current
    DESCRIPTION
        "Each row contains the status of a single QCE."
    INDEX       { gamQosStatusQceSwitchId, gamQosStatusQceIndex }
    ::= { gamQosStatusQceTable 1 }

GAMQosStatusQceEntry ::= SEQUENCE {
    gamQosStatusQceSwitchId  Unsigned32,
    gamQosStatusQceIndex     Integer32,
    gamQosStatusQceUserId    GAMQosQceUserType,
    gamQosStatusQceQceId     Unsigned32,
    gamQosStatusQceConflict  TruthValue
}

gamQosStatusQceSwitchId OBJECT-TYPE
    SYNTAX      Unsigned32
    MAX-ACCESS  accessible-for-notify
    STATUS      current
    DESCRIPTION
        "Switch Id index.
         
         This object is only available if the capability object
         'gamQosCapabilitiesHasQce' is True."
    ::= { gamQosStatusQceEntry 1 }

gamQosStatusQceIndex OBJECT-TYPE
    SYNTAX      Integer32 (0..2147483647)
    MAX-ACCESS  accessible-for-notify
    STATUS      current
    DESCRIPTION
        "QCE precedence index. Indicates the position in QCL.
         
         This object is only available if the capability object
         'gamQosCapabilitiesHasQce' is True."
    ::= { gamQosStatusQceEntry 2 }

gamQosStatusQceUserId OBJECT-TYPE
    SYNTAX      GAMQosQceUserType
    MAX-ACCESS  read-only
    STATUS      current
    DESCRIPTION
        "User Id.
         
         This object is only available if the capability object
         'gamQosCapabilitiesHasQce' is True."
    ::= { gamQosStatusQceEntry 3 }

gamQosStatusQceQceId OBJECT-TYPE
    SYNTAX      Unsigned32
    MAX-ACCESS  read-only
    STATUS      current
    DESCRIPTION
        "QCE Id.
         
         This object is only available if the capability object
         'gamQosCapabilitiesHasQce' is True."
    ::= { gamQosStatusQceEntry 4 }

gamQosStatusQceConflict OBJECT-TYPE
    SYNTAX      TruthValue
    MAX-ACCESS  read-only
    STATUS      current
    DESCRIPTION
        "If true, a resource conflict is detected.
         
         This object is only available if the capability object
         'gamQosCapabilitiesHasQce' is True."
    ::= { gamQosStatusQceEntry 100 }

gamQosStatusPsfp OBJECT IDENTIFIER
    ::= { gamQosStatus 4 }

gamQosStatusPsfpStreamParameters OBJECT IDENTIFIER
    ::= { gamQosStatusPsfp 1 }

gamQosStatusPsfpStreamParametersPsfpStreamFilteringInstanceMax OBJECT-TYPE
    SYNTAX      GAMUnsigned16
    MAX-ACCESS  read-only
    STATUS      current
    DESCRIPTION
        "The maximum number of Stream Filter instances supported."
    ::= { gamQosStatusPsfpStreamParameters 1 }

gamQosStatusPsfpStreamParametersPsfpStreamGateInstanceMax OBJECT-TYPE
    SYNTAX      GAMUnsigned16
    MAX-ACCESS  read-only
    STATUS      current
    DESCRIPTION
        "The maximum number of Stream Gate instances supported."
    ::= { gamQosStatusPsfpStreamParameters 2 }

gamQosStatusPsfpStreamParametersPsfpFlowMeterInstanceMax OBJECT-TYPE
    SYNTAX      GAMUnsigned16
    MAX-ACCESS  read-only
    STATUS      current
    DESCRIPTION
        "The maximum number of Flow Meter instances supported."
    ::= { gamQosStatusPsfpStreamParameters 3 }

gamQosStatusPsfpStreamParametersPsfpAdminControlListMax OBJECT-TYPE
    SYNTAX      GAMUnsigned16
    MAX-ACCESS  read-only
    STATUS      current
    DESCRIPTION
        "The maximum value supported in admin_control_list_length."
    ::= { gamQosStatusPsfpStreamParameters 4 }

gamQosStatusPsfpSfiTable OBJECT-TYPE
    SYNTAX      SEQUENCE OF GAMQosStatusPsfpSfiEntry
    MAX-ACCESS  not-accessible
    STATUS      current
    DESCRIPTION
        "This table contains the counters of PSFP SFI's. The index is SFIId.
         
         This is an optional table and is only present if qosCapabilitiesHasPsfp
         is true."
    ::= { gamQosStatusPsfp 2 }

gamQosStatusPsfpSfiEntry OBJECT-TYPE
    SYNTAX      GAMQosStatusPsfpSfiEntry
    MAX-ACCESS  not-accessible
    STATUS      current
    DESCRIPTION
        "Each row contains the counters of a single PSFP SFI."
    INDEX       { gamQosStatusPsfpSfiSfiId }
    ::= { gamQosStatusPsfpSfiTable 1 }

GAMQosStatusPsfpSfiEntry ::= SEQUENCE {
    gamQosStatusPsfpSfiSfiId                  Integer32,
    gamQosStatusPsfpSfiMatchingFramesCount    Counter64,
    gamQosStatusPsfpSfiPassingFramesCount     Counter64,
    gamQosStatusPsfpSfiNotPassingFramesCount  Counter64,
    gamQosStatusPsfpSfiPassingSDUCount        Counter64,
    gamQosStatusPsfpSfiNotPassingSDUCount     Counter64,
    gamQosStatusPsfpSfiREDFramesCount         Counter64
}

gamQosStatusPsfpSfiSfiId OBJECT-TYPE
    SYNTAX      Integer32 (0..2147483647)
    MAX-ACCESS  accessible-for-notify
    STATUS      current
    DESCRIPTION
        "SFI Id.
         
         
         
         This object is only available if the capability object
         'gamQosCapabilitiesHasPsfp' is True."
    ::= { gamQosStatusPsfpSfiEntry 1 }

gamQosStatusPsfpSfiMatchingFramesCount OBJECT-TYPE
    SYNTAX      Counter64
    MAX-ACCESS  read-only
    STATUS      current
    DESCRIPTION
        "The MatchingFramesCount counter counts received frames that match this
         stream filter.
         
         This object is only available if the capability object
         'gamQosCapabilitiesHasPsfp' is True."
    ::= { gamQosStatusPsfpSfiEntry 2 }

gamQosStatusPsfpSfiPassingFramesCount OBJECT-TYPE
    SYNTAX      Counter64
    MAX-ACCESS  read-only
    STATUS      current
    DESCRIPTION
        "The PassingFramesCount counter counts received frames that pass the
         gate associated with this stream filter.
         
         This object is only available if the capability object
         'gamQosCapabilitiesHasPsfp' is True."
    ::= { gamQosStatusPsfpSfiEntry 3 }

gamQosStatusPsfpSfiNotPassingFramesCount OBJECT-TYPE
    SYNTAX      Counter64
    MAX-ACCESS  read-only
    STATUS      current
    DESCRIPTION
        "The NotPassingFramesCount counter counts received frames that do not
         pass the gate associated with this stream filter.
         
         This object is only available if the capability object
         'gamQosCapabilitiesHasPsfp' is True."
    ::= { gamQosStatusPsfpSfiEntry 4 }

gamQosStatusPsfpSfiPassingSDUCount OBJECT-TYPE
    SYNTAX      Counter64
    MAX-ACCESS  read-only
    STATUS      current
    DESCRIPTION
        "The PassingSDUCount counter counts received frames that pass the SDU
         size filter specification associated with this stream filter.
         
         This object is only available if the capability object
         'gamQosCapabilitiesHasPsfp' is True."
    ::= { gamQosStatusPsfpSfiEntry 5 }

gamQosStatusPsfpSfiNotPassingSDUCount OBJECT-TYPE
    SYNTAX      Counter64
    MAX-ACCESS  read-only
    STATUS      current
    DESCRIPTION
        "The NotPassingSDUCount counter counts received frames that do not pass
         the SDU size filter specification associated with this stream filter.
         
         This object is only available if the capability object
         'gamQosCapabilitiesHasPsfp' is True."
    ::= { gamQosStatusPsfpSfiEntry 6 }

gamQosStatusPsfpSfiREDFramesCount OBJECT-TYPE
    SYNTAX      Counter64
    MAX-ACCESS  read-only
    STATUS      current
    DESCRIPTION
        "The REDFramesCount counter counts received random early detection (RED)
         frames associated with this stream filter.
         
         This object is only available if the capability object
         'gamQosCapabilitiesHasPsfp' is True."
    ::= { gamQosStatusPsfpSfiEntry 7 }

gamQosStatusPsfpGclTable OBJECT-TYPE
    SYNTAX      SEQUENCE OF GAMQosStatusPsfpGclEntry
    MAX-ACCESS  not-accessible
    STATUS      current
    DESCRIPTION
        "A table containing the operational entries/TLVs of the GCL, as defined
         in IEEE 802.1Qci"
    ::= { gamQosStatusPsfp 3 }

gamQosStatusPsfpGclEntry OBJECT-TYPE
    SYNTAX      GAMQosStatusPsfpGclEntry
    MAX-ACCESS  not-accessible
    STATUS      current
    DESCRIPTION
        "Each row contains single GCL entry with a unique gcl_index"
    INDEX       { gamQosStatusPsfpGclSgiId, gamQosStatusPsfpGclGclId }
    ::= { gamQosStatusPsfpGclTable 1 }

GAMQosStatusPsfpGclEntry ::= SEQUENCE {
    gamQosStatusPsfpGclSgiId         Integer32,
    gamQosStatusPsfpGclGclId         Integer32,
    gamQosStatusPsfpGclGateState     TruthValue,
    gamQosStatusPsfpGclIPV           GAMInteger8,
    gamQosStatusPsfpGclTimeInterval  Unsigned32,
    gamQosStatusPsfpGclOctetMax      Unsigned32
}

gamQosStatusPsfpGclSgiId OBJECT-TYPE
    SYNTAX      Integer32 (0..2147483647)
    MAX-ACCESS  accessible-for-notify
    STATUS      current
    DESCRIPTION
        "SGI Id.
         
         
         
         This object is only available if the capability object
         'gamQosCapabilitiesHasPsfp' is True."
    ::= { gamQosStatusPsfpGclEntry 1 }

gamQosStatusPsfpGclGclId OBJECT-TYPE
    SYNTAX      Integer32 (0..2147483647)
    MAX-ACCESS  accessible-for-notify
    STATUS      current
    DESCRIPTION
        "GCL Id.
         
         
         
         This object is only available if the capability object
         'gamQosCapabilitiesHasPsfp' is True."
    ::= { gamQosStatusPsfpGclEntry 2 }

gamQosStatusPsfpGclGateState OBJECT-TYPE
    SYNTAX      TruthValue
    MAX-ACCESS  read-only
    STATUS      current
    DESCRIPTION
        "The GateState parameter specifies a desired state,
         
         open (true) or closed (false), for the stream gate.
         
         
         
         This object is only available if the capability object
         'gamQosCapabilitiesHasPsfp' is True."
    ::= { gamQosStatusPsfpGclEntry 3 }

gamQosStatusPsfpGclIPV OBJECT-TYPE
    SYNTAX      GAMInteger8
    MAX-ACCESS  read-only
    STATUS      current
    DESCRIPTION
        "An IPV is encoded as a signed integer.
         
         A negative denotes the null value;
         
         zero or positive values denote internal priority values.
         
         
         
         This object is only available if the capability object
         'gamQosCapabilitiesHasPsfp' is True."
    ::= { gamQosStatusPsfpGclEntry 4 }

gamQosStatusPsfpGclTimeInterval OBJECT-TYPE
    SYNTAX      Unsigned32
    MAX-ACCESS  read-only
    STATUS      current
    DESCRIPTION
        "A TimeInterval is encoded in 4 octets as a 32-bit
         
         unsigned integer, representing a number of nanoseconds.
         
         
         
         This object is only available if the capability object
         'gamQosCapabilitiesHasPsfp' is True."
    ::= { gamQosStatusPsfpGclEntry 5 }

gamQosStatusPsfpGclOctetMax OBJECT-TYPE
    SYNTAX      Unsigned32
    MAX-ACCESS  read-only
    STATUS      current
    DESCRIPTION
        "The maximum number of octets that are permitted to pass
         
         the gate during the specified TimeInterval.
         
         If zero, there is no maximum.
         
         
         
         This object is only available if the capability object
         'gamQosCapabilitiesHasPsfp' is True."
    ::= { gamQosStatusPsfpGclEntry 6 }

gamQosStatusPsfpSgiTable OBJECT-TYPE
    SYNTAX      SEQUENCE OF GAMQosStatusPsfpSgiEntry
    MAX-ACCESS  not-accessible
    STATUS      current
    DESCRIPTION
        "This table contains the status of PSFP SGI. The index is SGI ID"
    ::= { gamQosStatusPsfp 4 }

gamQosStatusPsfpSgiEntry OBJECT-TYPE
    SYNTAX      GAMQosStatusPsfpSgiEntry
    MAX-ACCESS  not-accessible
    STATUS      current
    DESCRIPTION
        "Each row contains the status of a single PSFP SGI."
    INDEX       { gamQosStatusPsfpSgiSgiId }
    ::= { gamQosStatusPsfpSgiTable 1 }

GAMQosStatusPsfpSgiEntry ::= SEQUENCE {
    gamQosStatusPsfpSgiSgiId                     Integer32,
    gamQosStatusPsfpSgiOperGateStates            TruthValue,
    gamQosStatusPsfpSgiOperControlListLength     GAMUnsigned8,
    gamQosStatusPsfpSgiOperCycleTimeNumerator    Unsigned32,
    gamQosStatusPsfpSgiOperCycleTimeDenominator  Unsigned32,
    gamQosStatusPsfpSgiOperCycleTimeExtension    Unsigned32,
    gamQosStatusPsfpSgiOperBaseTime              IEEE8021STPTPtimeValue,
    gamQosStatusPsfpSgiConfigChangeTime          IEEE8021STPTPtimeValue,
    gamQosStatusPsfpSgiTickGranularity           Unsigned32,
    gamQosStatusPsfpSgiCurrentTime               IEEE8021STPTPtimeValue,
    gamQosStatusPsfpSgiConfigPending             TruthValue,
    gamQosStatusPsfpSgiConfigChangeError         GAMUnsigned64,
    gamQosStatusPsfpSgiOperIPV                   GAMInteger8
}

gamQosStatusPsfpSgiSgiId OBJECT-TYPE
    SYNTAX      Integer32 (0..2147483647)
    MAX-ACCESS  accessible-for-notify
    STATUS      current
    DESCRIPTION
        "SGI Id.
         
         
         
         This object is only available if the capability object
         'gamQosCapabilitiesHasPsfp' is True."
    ::= { gamQosStatusPsfpSgiEntry 1 }

gamQosStatusPsfpSgiOperGateStates OBJECT-TYPE
    SYNTAX      TruthValue
    MAX-ACCESS  read-only
    STATUS      current
    DESCRIPTION
        "The operational value of the GateStates parameter
         
         for the stream gate.
         
         A value of false indicates closed; a value of true indicates open.
         
         
         
         This object is only available if the capability object
         'gamQosCapabilitiesHasPsfp' is True."
    ::= { gamQosStatusPsfpSgiEntry 2 }

gamQosStatusPsfpSgiOperControlListLength OBJECT-TYPE
    SYNTAX      GAMUnsigned8
    MAX-ACCESS  read-only
    STATUS      current
    DESCRIPTION
        "The operational value of the ListMax parameter for the gate.
         
         The integer value indicates the number of entries (TLVs) in the
         
         OperControlList.
         
         
         
         This object is only available if the capability object
         'gamQosCapabilitiesHasPsfp' is True."
    ::= { gamQosStatusPsfpSgiEntry 3 }

gamQosStatusPsfpSgiOperCycleTimeNumerator OBJECT-TYPE
    SYNTAX      Unsigned32
    MAX-ACCESS  read-only
    STATUS      current
    DESCRIPTION
        "The operational value of the numerator of the
         
         CycleTime parameter for the gate.
         
         The numerator and denominator together represent the cycle
         
         time as a rational number of seconds.
         
         
         
         This object is only available if the capability object
         'gamQosCapabilitiesHasPsfp' is True."
    ::= { gamQosStatusPsfpSgiEntry 4 }

gamQosStatusPsfpSgiOperCycleTimeDenominator OBJECT-TYPE
    SYNTAX      Unsigned32
    MAX-ACCESS  read-only
    STATUS      current
    DESCRIPTION
        "The operational value of the denominator of the
         
         CycleTime parameter for the gate.
         
         The numerator and denominator together represent the
         
         cycle time as a rational number of seconds.
         
         
         
         This object is only available if the capability object
         'gamQosCapabilitiesHasPsfp' is True."
    ::= { gamQosStatusPsfpSgiEntry 5 }

gamQosStatusPsfpSgiOperCycleTimeExtension OBJECT-TYPE
    SYNTAX      Unsigned32
    MAX-ACCESS  read-only
    STATUS      current
    DESCRIPTION
        "The operational value of the CycleTimeExtension parameter for the gate.
         
         The value is an unsigned integer number of nanoseconds.
         
         
         
         This object is only available if the capability object
         'gamQosCapabilitiesHasPsfp' is True."
    ::= { gamQosStatusPsfpSgiEntry 6 }

gamQosStatusPsfpSgiOperBaseTime OBJECT-TYPE
    SYNTAX      IEEE8021STPTPtimeValue
    MAX-ACCESS  read-only
    STATUS      current
    DESCRIPTION
        "The operationsl value of the BaseTime parameter for the gate.
         
         The value is a representation of a PTPtime value,
         
         consisting of a 48-bit integer
         
         number of seconds and a 32-bit integer number of nanoseconds.
         
         
         
         This object is only available if the capability object
         'gamQosCapabilitiesHasPsfp' is True."
    ::= { gamQosStatusPsfpSgiEntry 7 }

gamQosStatusPsfpSgiConfigChangeTime OBJECT-TYPE
    SYNTAX      IEEE8021STPTPtimeValue
    MAX-ACCESS  read-only
    STATUS      current
    DESCRIPTION
        "The PTPtime at which the next config change is scheduled to occur.
         
         The value is a representation of a PTPtime value,
         
         consisting of a 48-bit integer
         
         number of seconds and a 32-bit integer number of nanoseconds.
         
         
         
         This object is only available if the capability object
         'gamQosCapabilitiesHasPsfp' is True."
    ::= { gamQosStatusPsfpSgiEntry 8 }

gamQosStatusPsfpSgiTickGranularity OBJECT-TYPE
    SYNTAX      Unsigned32
    MAX-ACCESS  read-only
    STATUS      current
    DESCRIPTION
        "The granularity of the cycle time clock, represented as an
         
         unsigned number of tenths of nanoseconds.
         
         
         
         This object is only available if the capability object
         'gamQosCapabilitiesHasPsfp' is True."
    ::= { gamQosStatusPsfpSgiEntry 9 }

gamQosStatusPsfpSgiCurrentTime OBJECT-TYPE
    SYNTAX      IEEE8021STPTPtimeValue
    MAX-ACCESS  read-only
    STATUS      current
    DESCRIPTION
        "The current time, in PTPtime, as maintained by the local system.
         
         The value is a representation of a PTPtime value,
         
         consisting of a 48-bit integer
         
         number of seconds and a 32-bit integer number of nanoseconds.
         
         
         
         This object is only available if the capability object
         'gamQosCapabilitiesHasPsfp' is True."
    ::= { gamQosStatusPsfpSgiEntry 10 }

gamQosStatusPsfpSgiConfigPending OBJECT-TYPE
    SYNTAX      TruthValue
    MAX-ACCESS  read-only
    STATUS      current
    DESCRIPTION
        "The value of the ConfigPending state machine variable.
         
         The value is TRUE if a configuration change is in progress
         
         but has not yet completed.
         
         
         
         This object is only available if the capability object
         'gamQosCapabilitiesHasPsfp' is True."
    ::= { gamQosStatusPsfpSgiEntry 11 }

gamQosStatusPsfpSgiConfigChangeError OBJECT-TYPE
    SYNTAX      GAMUnsigned64
    MAX-ACCESS  read-only
    STATUS      current
    DESCRIPTION
        "A counter of the number of times that a re-configuration
         
         of the traffic schedule has been requested with the old
         
         schedule still running and the requested base time was
         
         in the past.
         
         
         
         This object is only available if the capability object
         'gamQosCapabilitiesHasPsfp' is True."
    ::= { gamQosStatusPsfpSgiEntry 12 }

gamQosStatusPsfpSgiOperIPV OBJECT-TYPE
    SYNTAX      GAMInteger8
    MAX-ACCESS  read-only
    STATUS      current
    DESCRIPTION
        "The operational value of the IPV parameter for the gate.
         
         A value of -1 denotes the null value;
         
         zero or positive values denote internal priority values.
         
         
         
         This object is only available if the capability object
         'gamQosCapabilitiesHasPsfp' is True."
    ::= { gamQosStatusPsfpSgiEntry 13 }

gamQosControl OBJECT IDENTIFIER
    ::= { gamQosMibObjects 4 }

gamQosControlQce OBJECT IDENTIFIER
    ::= { gamQosControl 3 }

gamQosControlQceConflictResolve OBJECT-TYPE
    SYNTAX      TruthValue
    MAX-ACCESS  read-write
    STATUS      current
    DESCRIPTION
        "Set to true to resolve resource conflicts.
         
         If different components competes for the same resources in the switch,
         it is possible that some of resources needed by one or more QCE are not
         available.
         
         These conflicts, if any, are shown in the qosStatusQceTable.
         
         To solve these conflicts, you must delete one or more of the competing
         settings and set ConflictResolve to true. The switch will then reapply
         the current QCE configuration.
         
         
         
         This object is only available if the capability object
         'gamQosCapabilitiesHasQce' is True."
    ::= { gamQosControlQce 1 }

gamQosControlPsfpSfiCountersTable OBJECT-TYPE
    SYNTAX      SEQUENCE OF GAMQosControlPsfpSfiCountersEntry
    MAX-ACCESS  not-accessible
    STATUS      current
    DESCRIPTION
        "This is a table to clear counters"
    ::= { gamQosControl 4 }

gamQosControlPsfpSfiCountersEntry OBJECT-TYPE
    SYNTAX      GAMQosControlPsfpSfiCountersEntry
    MAX-ACCESS  not-accessible
    STATUS      current
    DESCRIPTION
        "Each row contains set of counters"
    INDEX       { gamQosControlPsfpSfiCountersSfiId }
    ::= { gamQosControlPsfpSfiCountersTable 1 }

GAMQosControlPsfpSfiCountersEntry ::= SEQUENCE {
    gamQosControlPsfpSfiCountersSfiId  Integer32,
    gamQosControlPsfpSfiCountersClear  TruthValue
}

gamQosControlPsfpSfiCountersSfiId OBJECT-TYPE
    SYNTAX      Integer32 (0..2147483647)
    MAX-ACCESS  accessible-for-notify
    STATUS      current
    DESCRIPTION
        "SFI Id.
         
         
         
         This object is only available if the capability object
         'gamQosCapabilitiesHasPsfp' is True."
    ::= { gamQosControlPsfpSfiCountersEntry 1 }

gamQosControlPsfpSfiCountersClear OBJECT-TYPE
    SYNTAX      TruthValue
    MAX-ACCESS  read-write
    STATUS      current
    DESCRIPTION
        "Set to TRUE to clear PSFP SFI counters.
         
         This object is only available if the capability object
         'gamQosCapabilitiesHasPsfp' is True."
    ::= { gamQosControlPsfpSfiCountersEntry 2 }

gamQosMibConformance OBJECT IDENTIFIER
    ::= { gamQosMib 2 }

gamQosMibCompliances OBJECT IDENTIFIER
    ::= { gamQosMibConformance 1 }

gamQosMibGroups OBJECT IDENTIFIER
    ::= { gamQosMibConformance 2 }

gamQosCapabilitiesInfoGroup OBJECT-GROUP
    OBJECTS     { gamQosCapabilitiesClassMin,
                  gamQosCapabilitiesClassMax,
                  gamQosCapabilitiesDplMin, gamQosCapabilitiesDplMax,
                  gamQosCapabilitiesWredGroupMin,
                  gamQosCapabilitiesWredGroupMax,
                  gamQosCapabilitiesWredDplMin,
                  gamQosCapabilitiesWredDplMax,
                  gamQosCapabilitiesQceIdMin,
                  gamQosCapabilitiesQceIdMax,
                  gamQosCapabilitiesPortPolicerBitRateMin,
                  gamQosCapabilitiesPortPolicerBitRateMax,
                  gamQosCapabilitiesPortPolicerBitBurstMin,
                  gamQosCapabilitiesPortPolicerBitBurstMax,
                  gamQosCapabilitiesPortPolicerFrameRateMin,
                  gamQosCapabilitiesPortPolicerFrameRateMax,
                  gamQosCapabilitiesPortPolicerFrameBurstMin,
                  gamQosCapabilitiesPortPolicerFrameBurstMax,
                  gamQosCapabilitiesQueuePolicerBitRateMin,
                  gamQosCapabilitiesQueuePolicerBitRateMax,
                  gamQosCapabilitiesQueuePolicerBitBurstMin,
                  gamQosCapabilitiesQueuePolicerBitBurstMax,
                  gamQosCapabilitiesQueuePolicerFrameRateMin,
                  gamQosCapabilitiesQueuePolicerFrameRateMax,
                  gamQosCapabilitiesQueuePolicerFrameBurstMin,
                  gamQosCapabilitiesQueuePolicerFrameBurstMax,
                  gamQosCapabilitiesPortShaperBitRateMin,
                  gamQosCapabilitiesPortShaperBitRateMax,
                  gamQosCapabilitiesPortShaperBitBurstMin,
                  gamQosCapabilitiesPortShaperBitBurstMax,
                  gamQosCapabilitiesPortShaperFrameRateMin,
                  gamQosCapabilitiesPortShaperFrameRateMax,
                  gamQosCapabilitiesPortShaperFrameBurstMin,
                  gamQosCapabilitiesPortShaperFrameBurstMax,
                  gamQosCapabilitiesQueueShaperBitRateMin,
                  gamQosCapabilitiesQueueShaperBitRateMax,
                  gamQosCapabilitiesQueueShaperBitBurstMin,
                  gamQosCapabilitiesQueueShaperBitBurstMax,
                  gamQosCapabilitiesQueueShaperFrameRateMin,
                  gamQosCapabilitiesQueueShaperFrameRateMax,
                  gamQosCapabilitiesQueueShaperFrameBurstMin,
                  gamQosCapabilitiesQueueShaperFrameBurstMax,
                  gamQosCapabilitiesGlobalStormBitRateMin,
                  gamQosCapabilitiesGlobalStormBitRateMax,
                  gamQosCapabilitiesGlobalStormBitBurstMin,
                  gamQosCapabilitiesGlobalStormBitBurstMax,
                  gamQosCapabilitiesGlobalStormFrameRateMin,
                  gamQosCapabilitiesGlobalStormFrameRateMax,
                  gamQosCapabilitiesGlobalStormFrameBurstMin,
                  gamQosCapabilitiesGlobalStormFrameBurstMax,
                  gamQosCapabilitiesPortStormBitRateMin,
                  gamQosCapabilitiesPortStormBitRateMax,
                  gamQosCapabilitiesPortStormBitBurstMin,
                  gamQosCapabilitiesPortStormBitBurstMax,
                  gamQosCapabilitiesPortStormFrameRateMin,
                  gamQosCapabilitiesPortStormFrameRateMax,
                  gamQosCapabilitiesPortStormFrameBurstMin,
                  gamQosCapabilitiesPortStormFrameBurstMax,
                  gamQosCapabilitiesIngressMapIdMin,
                  gamQosCapabilitiesIngressMapIdMax,
                  gamQosCapabilitiesEgressMapIdMin,
                  gamQosCapabilitiesEgressMapIdMax,
                  gamQosCapabilitiesCosIdMin,
                  gamQosCapabilitiesCosIdMax,
                  gamQosCapabilitiesQbvGclLenMax,
                  gamQosCapabilitiesDwrrCountMask,
                  gamQosCapabilitiesHasGlobalStormPolicers,
                  gamQosCapabilitiesHasPortStormPolicers,
                  gamQosCapabilitiesHasPortQueuePolicers,
                  gamQosCapabilitiesHasWredV1,
                  gamQosCapabilitiesHasWredV2,
                  gamQosCapabilitiesHasFixedTagCosMap,
                  gamQosCapabilitiesHasTagClassification,
                  gamQosCapabilitiesHasTagRemarking,
                  gamQosCapabilitiesHasDscp,
                  gamQosCapabilitiesHasDscpDplClassification,
                  gamQosCapabilitiesHasDscpDplRemarking,
                  gamQosCapabilitiesHasPortPolicersFc,
                  gamQosCapabilitiesHasQueuePolicersFc,
                  gamQosCapabilitiesHasPortShapersDlb,
                  gamQosCapabilitiesHasQueueShapersDlb,
                  gamQosCapabilitiesHasQueueShapersExcess,
                  gamQosCapabilitiesHasWredV3,
                  gamQosCapabilitiesHasQueueShapersCredit,
                  gamQosCapabilitiesHasQueueCutThrough,
                  gamQosCapabilitiesHasQueueFramePreemption,
                  gamQosCapabilitiesHasQce,
                  gamQosCapabilitiesHasQceAddressMode,
                  gamQosCapabilitiesHasQceKeyType,
                  gamQosCapabilitiesHasQceMacOui,
                  gamQosCapabilitiesHasQceDmac,
                  gamQosCapabilitiesHasQceDip,
                  gamQosCapabilitiesHasQceCTag,
                  gamQosCapabilitiesHasQceSTag,
                  gamQosCapabilitiesHasQceInnerTag,
                  gamQosCapabilitiesHasQceActionPcpDei,
                  gamQosCapabilitiesHasQceActionPolicy,
                  gamQosCapabilitiesHasShapersRt,
                  gamQosCapabilitiesHasQceActionMap,
                  gamQosCapabilitiesHasIngressMap,
                  gamQosCapabilitiesHasEgressMap,
                  gamQosCapabilitiesHasWred2orWredw3,
                  gamQosCapabilitiesHasDscpDp2,
                  gamQosCapabilitiesHasDscpDp3,
                  gamQosCapabilitiesHasDefaultPcpAndDei,
                  gamQosCapabilitiesHasTrustTag,
                  gamQosCapabilitiesHasCosIdClassification,
                  gamQosCapabilitiesHasQbv, gamQosCapabilitiesHasWred,
                  gamQosCapabilitiesHasPsfp }
    STATUS      current
    DESCRIPTION
        "A collection of objects."
    ::= { gamQosMibGroups 1 }

gamQosConfigGlobalsStormPolicersUnicastInfoGroup OBJECT-GROUP
    OBJECTS     { gamQosConfigGlobalsStormPolicersUnicastEnable,
                  gamQosConfigGlobalsStormPolicersUnicastRate,
                  gamQosConfigGlobalsStormPolicersUnicastFrameRate }
    STATUS      current
    DESCRIPTION
        "A collection of objects."
    ::= { gamQosMibGroups 2 }

gamQosConfigGlobalsStormPolicersMulticastInfoGroup OBJECT-GROUP
    OBJECTS     { gamQosConfigGlobalsStormPolicersMulticastEnable,
                  gamQosConfigGlobalsStormPolicersMulticastRate,
                  gamQosConfigGlobalsStormPolicersMulticastFrameRate }
    STATUS      current
    DESCRIPTION
        "A collection of objects."
    ::= { gamQosMibGroups 3 }

gamQosConfigGlobalsStormPolicersBroadcastInfoGroup OBJECT-GROUP
    OBJECTS     { gamQosConfigGlobalsStormPolicersBroadcastEnable,
                  gamQosConfigGlobalsStormPolicersBroadcastRate,
                  gamQosConfigGlobalsStormPolicersBroadcastFrameRate }
    STATUS      current
    DESCRIPTION
        "A collection of objects."
    ::= { gamQosMibGroups 4 }

gamQosConfigGlobalsWredTableInfoGroup OBJECT-GROUP
    OBJECTS     { gamQosConfigGlobalsWredGroup,
                  gamQosConfigGlobalsWredQueue,
                  gamQosConfigGlobalsWredDpl,
                  gamQosConfigGlobalsWredEnable,
                  gamQosConfigGlobalsWredMinimumFillLevel,
                  gamQosConfigGlobalsWredMaximum,
                  gamQosConfigGlobalsWredMaxSelector,
                  gamQosConfigGlobalsWredMaximumDp1,
                  gamQosConfigGlobalsWredMaximumDp2,
                  gamQosConfigGlobalsWredMaximumDp3 }
    STATUS      current
    DESCRIPTION
        "A collection of objects."
    ::= { gamQosMibGroups 5 }

gamQosConfigGlobalsDscpTableInfoGroup OBJECT-GROUP
    OBJECTS     { gamQosConfigGlobalsDscpDscp,
                  gamQosConfigGlobalsDscpTrust,
                  gamQosConfigGlobalsDscpCos,
                  gamQosConfigGlobalsDscpDpl,
                  gamQosConfigGlobalsDscpIngressTranslation,
                  gamQosConfigGlobalsDscpClassify,
                  gamQosConfigGlobalsDscpEgressTranslation,
                  gamQosConfigGlobalsDscpEgressTranslationDp1 }
    STATUS      current
    DESCRIPTION
        "A collection of objects."
    ::= { gamQosMibGroups 6 }

gamQosConfigGlobalsCosToDscpTableInfoGroup OBJECT-GROUP
    OBJECTS     { gamQosConfigGlobalsCosToDscpCos,
                  gamQosConfigGlobalsCosToDscpDscp,
                  gamQosConfigGlobalsCosToDscpDscpDp1,
                  gamQosConfigGlobalsCosToDscpDscpDp2,
                  gamQosConfigGlobalsCosToDscpDscpDp3 }
    STATUS      current
    DESCRIPTION
        "A collection of objects."
    ::= { gamQosMibGroups 7 }

gamQosConfigGlobalsPcpCosMapTableInfoGroup OBJECT-GROUP
    OBJECTS     { gamQosConfigGlobalsPcpCosMapPcp,
                  gamQosConfigGlobalsPcpCosMapCos }
    STATUS      current
    DESCRIPTION
        "A collection of objects."
    ::= { gamQosMibGroups 8 }

gamQosConfigInterfaceTableInfoGroup OBJECT-GROUP
    OBJECTS     { gamQosConfigInterfaceIfIndex,
                  gamQosConfigInterfaceCos, gamQosConfigInterfaceDpl,
                  gamQosConfigInterfacePcp, gamQosConfigInterfaceDei,
                  gamQosConfigInterfaceTrustTag,
                  gamQosConfigInterfaceTrustDscp,
                  gamQosConfigInterfaceDwrrCount,
                  gamQosConfigInterfaceTagRemarkingMode,
                  gamQosConfigInterfaceTagPcp,
                  gamQosConfigInterfaceTagDei,
                  gamQosConfigInterfaceDscpTranslate,
                  gamQosConfigInterfaceDscpClassify,
                  gamQosConfigInterfaceDscpRemark,
                  gamQosConfigInterfaceQceAddressMode,
                  gamQosConfigInterfaceQceKeyType,
                  gamQosConfigInterfaceWredGroup,
                  gamQosConfigInterfaceIngressMap,
                  gamQosConfigInterfaceEgressMap,
                  gamQosConfigInterfaceCosId }
    STATUS      current
    DESCRIPTION
        "A collection of objects."
    ::= { gamQosMibGroups 9 }

gamQosConfigInterfaceTagToCosTableInfoGroup OBJECT-GROUP
    OBJECTS     { gamQosConfigInterfaceTagToCosIfIndex,
                  gamQosConfigInterfaceTagToCosPcp,
                  gamQosConfigInterfaceTagToCosDei,
                  gamQosConfigInterfaceTagToCosCos,
                  gamQosConfigInterfaceTagToCosDpl }
    STATUS      current
    DESCRIPTION
        "A collection of objects."
    ::= { gamQosMibGroups 10 }

gamQosConfigInterfaceCosToTagTableInfoGroup OBJECT-GROUP
    OBJECTS     { gamQosConfigInterfaceCosToTagIfIndex,
                  gamQosConfigInterfaceCosToTagCos,
                  gamQosConfigInterfaceCosToTagDpl,
                  gamQosConfigInterfaceCosToTagPcp,
                  gamQosConfigInterfaceCosToTagDei }
    STATUS      current
    DESCRIPTION
        "A collection of objects."
    ::= { gamQosMibGroups 11 }

gamQosConfigInterfacePolicerTableInfoGroup OBJECT-GROUP
    OBJECTS     { gamQosConfigInterfacePolicerIfIndex,
                  gamQosConfigInterfacePolicerEnable,
                  gamQosConfigInterfacePolicerFrameRate,
                  gamQosConfigInterfacePolicerFlowControl,
                  gamQosConfigInterfacePolicerCir }
    STATUS      current
    DESCRIPTION
        "A collection of objects."
    ::= { gamQosMibGroups 12 }

gamQosConfigInterfaceQueuePolicerTableInfoGroup OBJECT-GROUP
    OBJECTS     { gamQosConfigInterfaceQueuePolicerIfIndex,
                  gamQosConfigInterfaceQueuePolicerQueue,
                  gamQosConfigInterfaceQueuePolicerEnable,
                  gamQosConfigInterfaceQueuePolicerCir }
    STATUS      current
    DESCRIPTION
        "A collection of objects."
    ::= { gamQosMibGroups 13 }

gamQosConfigInterfaceShaperTableInfoGroup OBJECT-GROUP
    OBJECTS     { gamQosConfigInterfaceShaperIfIndex,
                  gamQosConfigInterfaceShaperEnable,
                  gamQosConfigInterfaceShaperCir,
                  gamQosConfigInterfaceShaperRateType }
    STATUS      current
    DESCRIPTION
        "A collection of objects."
    ::= { gamQosMibGroups 14 }

gamQosConfigInterfaceQueueShaperTableInfoGroup OBJECT-GROUP
    OBJECTS     { gamQosConfigInterfaceQueueShaperIfIndex,
                  gamQosConfigInterfaceQueueShaperQueue,
                  gamQosConfigInterfaceQueueShaperEnable,
                  gamQosConfigInterfaceQueueShaperExcess,
                  gamQosConfigInterfaceQueueShaperCir,
                  gamQosConfigInterfaceQueueShaperRateType,
                  gamQosConfigInterfaceQueueShaperCredit }
    STATUS      current
    DESCRIPTION
        "A collection of objects."
    ::= { gamQosMibGroups 15 }

gamQosConfigInterfaceSchedulerTableInfoGroup OBJECT-GROUP
    OBJECTS     { gamQosConfigInterfaceSchedulerIfIndex,
                  gamQosConfigInterfaceSchedulerQueue,
                  gamQosConfigInterfaceSchedulerWeight,
                  gamQosConfigInterfaceSchedulerCutThrough,
                  gamQosConfigInterfaceSchedulerFramePreemption }
    STATUS      current
    DESCRIPTION
        "A collection of objects."
    ::= { gamQosMibGroups 16 }

gamQosConfigInterfaceStormPolicerUnicastTableInfoGroup OBJECT-GROUP
    OBJECTS     { gamQosConfigInterfaceStormPolicerUnicastIfIndex,
                  gamQosConfigInterfaceStormPolicerUnicastEnable,
                  gamQosConfigInterfaceStormPolicerUnicastFrameRate,
                  gamQosConfigInterfaceStormPolicerUnicastCir }
    STATUS      current
    DESCRIPTION
        "A collection of objects."
    ::= { gamQosMibGroups 17 }

gamQosConfigInterfaceStormPolicerBroadcastTableInfoGroup OBJECT-GROUP
    OBJECTS     { gamQosConfigInterfaceStormPolicerBroadcastIfIndex,
                  gamQosConfigInterfaceStormPolicerBroadcastEnable,
                  gamQosConfigInterfaceStormPolicerBroadcastFrameRate,
                  gamQosConfigInterfaceStormPolicerBroadcastCir }
    STATUS      current
    DESCRIPTION
        "A collection of objects."
    ::= { gamQosMibGroups 18 }

gamQosConfigInterfaceStormPolicerUnknownTableInfoGroup OBJECT-GROUP
    OBJECTS     { gamQosConfigInterfaceStormPolicerUnknownIfIndex,
                  gamQosConfigInterfaceStormPolicerUnknownEnable,
                  gamQosConfigInterfaceStormPolicerUnknownFrameRate,
                  gamQosConfigInterfaceStormPolicerUnknownCir }
    STATUS      current
    DESCRIPTION
        "A collection of objects."
    ::= { gamQosMibGroups 19 }

gamQosConfigInterfaceQbvMaxSduTableInfoGroup OBJECT-GROUP
    OBJECTS     { gamQosConfigInterfaceQbvMaxSduIfIndex,
                  gamQosConfigInterfaceQbvMaxSduQueue,
                  gamQosConfigInterfaceQbvMaxSduMaxSDU }
    STATUS      current
    DESCRIPTION
        "A collection of objects."
    ::= { gamQosMibGroups 20 }

gamQosConfigInterfaceQbvGclAdminTableInfoGroup OBJECT-GROUP
    OBJECTS     { gamQosConfigInterfaceQbvGclAdminIfIndex,
                  gamQosConfigInterfaceQbvGclAdminGclIndex,
                  gamQosConfigInterfaceQbvGclAdminGateState,
                  gamQosConfigInterfaceQbvGclAdminTimeInterval }
    STATUS      current
    DESCRIPTION
        "A collection of objects."
    ::= { gamQosMibGroups 21 }

gamQosConfigInterfaceQbvParamsTableInfoGroup OBJECT-GROUP
    OBJECTS     { gamQosConfigInterfaceQbvParamsIfIndex,
                  gamQosConfigInterfaceQbvParamsGateEnabled,
                  gamQosConfigInterfaceQbvParamsAdminGateStates,
                  gamQosConfigInterfaceQbvParamsAdminControlListLength,
                  gamQosConfigInterfaceQbvParamsAdminCycleTimeNumerator,
                  gamQosConfigInterfaceQbvParamsAdminCycleTimeDenominator,
                  gamQosConfigInterfaceQbvParamsAdminCycleTimeExtension,
                  gamQosConfigInterfaceQbvParamsAdminBaseTimeSecs,
                  gamQosConfigInterfaceQbvParamsAdminBaseTimeNanoSecs,
                  gamQosConfigInterfaceQbvParamsConfigChange }
    STATUS      current
    DESCRIPTION
        "A collection of objects."
    ::= { gamQosMibGroups 22 }

gamQosConfigInterfaceFpTableInfoGroup OBJECT-GROUP
    OBJECTS     { gamQosConfigInterfaceFpIfIndex,
                  gamQosConfigInterfaceFpEnableTx,
                  gamQosConfigInterfaceFpVerifyDisable }
    STATUS      current
    DESCRIPTION
        "A collection of objects."
    ::= { gamQosMibGroups 23 }

gamQosConfigQceTableInfoGroup OBJECT-GROUP
    OBJECTS     { gamQosConfigQceQceId, gamQosConfigQceNextQceId,
                  gamQosConfigQceSwitchId, gamQosConfigQcePortList,
                  gamQosConfigQceDestMacType, gamQosConfigQceDestMac,
                  gamQosConfigQceDestMacMask, gamQosConfigQceSrcMac,
                  gamQosConfigQceSrcMacMask,
                  gamQosConfigQceVlanTagType, gamQosConfigQceVlanIdOp,
                  gamQosConfigQceVlanId, gamQosConfigQceVlanIdRange,
                  gamQosConfigQcePcp, gamQosConfigQceDei,
                  gamQosConfigQceInnerVlanTagType,
                  gamQosConfigQceInnerVlanIdOp,
                  gamQosConfigQceInnerVlanId,
                  gamQosConfigQceInnerVlanIdRange,
                  gamQosConfigQceInnerPcp, gamQosConfigQceInnerDei,
                  gamQosConfigQceFrameType, gamQosConfigQceEtype,
                  gamQosConfigQceLlcDsap, gamQosConfigQceLlcDsapMask,
                  gamQosConfigQceLlcSsap, gamQosConfigQceLlcSsapMask,
                  gamQosConfigQceLlcControl,
                  gamQosConfigQceLlcControlMask,
                  gamQosConfigQceSnapPid, gamQosConfigQceSnapPidMask,
                  gamQosConfigQceIpv4Fragment,
                  gamQosConfigQceIpv4DscpOp, gamQosConfigQceIpv4Dscp,
                  gamQosConfigQceIpv4DscpRange,
                  gamQosConfigQceIpv4Protocol,
                  gamQosConfigQceIpv4ProtocolMask,
                  gamQosConfigQceIpv4SrcIp,
                  gamQosConfigQceIpv4SrcIpMask,
                  gamQosConfigQceIpv4DestIp,
                  gamQosConfigQceIpv4DestIpMask,
                  gamQosConfigQceIpv4SrcPortOp,
                  gamQosConfigQceIpv4SrcPort,
                  gamQosConfigQceIpv4SrcPortRange,
                  gamQosConfigQceIpv4DestPortOp,
                  gamQosConfigQceIpv4DestPort,
                  gamQosConfigQceIpv4DestPortRange,
                  gamQosConfigQceIpv6DscpOp, gamQosConfigQceIpv6Dscp,
                  gamQosConfigQceIpv6DscpRange,
                  gamQosConfigQceIpv6Protocol,
                  gamQosConfigQceIpv6ProtocolMask,
                  gamQosConfigQceIpv6SrcIp,
                  gamQosConfigQceIpv6SrcIpMask,
                  gamQosConfigQceIpv6DestIp,
                  gamQosConfigQceIpv6DestIpMask,
                  gamQosConfigQceIpv6SrcPortOp,
                  gamQosConfigQceIpv6SrcPort,
                  gamQosConfigQceIpv6SrcPortRange,
                  gamQosConfigQceIpv6DestPortOp,
                  gamQosConfigQceIpv6DestPort,
                  gamQosConfigQceIpv6DestPortRange,
                  gamQosConfigQceActionCosEnable,
                  gamQosConfigQceActionCos,
                  gamQosConfigQceActionDplEnable,
                  gamQosConfigQceActionDpl,
                  gamQosConfigQceActionDscpEnable,
                  gamQosConfigQceActionDscp,
                  gamQosConfigQceActionPcpDeiEnable,
                  gamQosConfigQceActionPcp, gamQosConfigQceActionDei,
                  gamQosConfigQceActionPolicyEnable,
                  gamQosConfigQceActionPolicy,
                  gamQosConfigQceActionMapEnable,
                  gamQosConfigQceActionMap, gamQosConfigQceAction }
    STATUS      current
    DESCRIPTION
        "A collection of objects."
    ::= { gamQosMibGroups 24 }

gamQosConfigQceTableRowEditorInfoGroup OBJECT-GROUP
    OBJECTS     { gamQosConfigQceTableRowEditorQceId,
                  gamQosConfigQceTableRowEditorNextQceId,
                  gamQosConfigQceTableRowEditorSwitchId,
                  gamQosConfigQceTableRowEditorPortList,
                  gamQosConfigQceTableRowEditorDestMacType,
                  gamQosConfigQceTableRowEditorDestMac,
                  gamQosConfigQceTableRowEditorDestMacMask,
                  gamQosConfigQceTableRowEditorSrcMac,
                  gamQosConfigQceTableRowEditorSrcMacMask,
                  gamQosConfigQceTableRowEditorVlanTagType,
                  gamQosConfigQceTableRowEditorVlanIdOp,
                  gamQosConfigQceTableRowEditorVlanId,
                  gamQosConfigQceTableRowEditorVlanIdRange,
                  gamQosConfigQceTableRowEditorPcp,
                  gamQosConfigQceTableRowEditorDei,
                  gamQosConfigQceTableRowEditorInnerVlanTagType,
                  gamQosConfigQceTableRowEditorInnerVlanIdOp,
                  gamQosConfigQceTableRowEditorInnerVlanId,
                  gamQosConfigQceTableRowEditorInnerVlanIdRange,
                  gamQosConfigQceTableRowEditorInnerPcp,
                  gamQosConfigQceTableRowEditorInnerDei,
                  gamQosConfigQceTableRowEditorFrameType,
                  gamQosConfigQceTableRowEditorEtype,
                  gamQosConfigQceTableRowEditorLlcDsap,
                  gamQosConfigQceTableRowEditorLlcDsapMask,
                  gamQosConfigQceTableRowEditorLlcSsap,
                  gamQosConfigQceTableRowEditorLlcSsapMask,
                  gamQosConfigQceTableRowEditorLlcControl,
                  gamQosConfigQceTableRowEditorLlcControlMask,
                  gamQosConfigQceTableRowEditorSnapPid,
                  gamQosConfigQceTableRowEditorSnapPidMask,
                  gamQosConfigQceTableRowEditorIpv4Fragment,
                  gamQosConfigQceTableRowEditorIpv4DscpOp,
                  gamQosConfigQceTableRowEditorIpv4Dscp,
                  gamQosConfigQceTableRowEditorIpv4DscpRange,
                  gamQosConfigQceTableRowEditorIpv4Protocol,
                  gamQosConfigQceTableRowEditorIpv4ProtocolMask,
                  gamQosConfigQceTableRowEditorIpv4SrcIp,
                  gamQosConfigQceTableRowEditorIpv4SrcIpMask,
                  gamQosConfigQceTableRowEditorIpv4DestIp,
                  gamQosConfigQceTableRowEditorIpv4DestIpMask,
                  gamQosConfigQceTableRowEditorIpv4SrcPortOp,
                  gamQosConfigQceTableRowEditorIpv4SrcPort,
                  gamQosConfigQceTableRowEditorIpv4SrcPortRange,
                  gamQosConfigQceTableRowEditorIpv4DestPortOp,
                  gamQosConfigQceTableRowEditorIpv4DestPort,
                  gamQosConfigQceTableRowEditorIpv4DestPortRange,
                  gamQosConfigQceTableRowEditorIpv6DscpOp,
                  gamQosConfigQceTableRowEditorIpv6Dscp,
                  gamQosConfigQceTableRowEditorIpv6DscpRange,
                  gamQosConfigQceTableRowEditorIpv6Protocol,
                  gamQosConfigQceTableRowEditorIpv6ProtocolMask,
                  gamQosConfigQceTableRowEditorIpv6SrcIp,
                  gamQosConfigQceTableRowEditorIpv6SrcIpMask,
                  gamQosConfigQceTableRowEditorIpv6DestIp,
                  gamQosConfigQceTableRowEditorIpv6DestIpMask,
                  gamQosConfigQceTableRowEditorIpv6SrcPortOp,
                  gamQosConfigQceTableRowEditorIpv6SrcPort,
                  gamQosConfigQceTableRowEditorIpv6SrcPortRange,
                  gamQosConfigQceTableRowEditorIpv6DestPortOp,
                  gamQosConfigQceTableRowEditorIpv6DestPort,
                  gamQosConfigQceTableRowEditorIpv6DestPortRange,
                  gamQosConfigQceTableRowEditorActionCosEnable,
                  gamQosConfigQceTableRowEditorActionCos,
                  gamQosConfigQceTableRowEditorActionDplEnable,
                  gamQosConfigQceTableRowEditorActionDpl,
                  gamQosConfigQceTableRowEditorActionDscpEnable,
                  gamQosConfigQceTableRowEditorActionDscp,
                  gamQosConfigQceTableRowEditorActionPcpDeiEnable,
                  gamQosConfigQceTableRowEditorActionPcp,
                  gamQosConfigQceTableRowEditorActionDei,
                  gamQosConfigQceTableRowEditorActionPolicyEnable,
                  gamQosConfigQceTableRowEditorActionPolicy,
                  gamQosConfigQceTableRowEditorActionMapEnable,
                  gamQosConfigQceTableRowEditorActionMap,
                  gamQosConfigQceTableRowEditorAction }
    STATUS      current
    DESCRIPTION
        "A collection of objects."
    ::= { gamQosMibGroups 25 }

gamQosConfigQcePrecedenceTableInfoGroup OBJECT-GROUP
    OBJECTS     { gamQosConfigQcePrecedenceIndex,
                  gamQosConfigQcePrecedenceQceId }
    STATUS      current
    DESCRIPTION
        "A collection of objects."
    ::= { gamQosMibGroups 26 }

gamQosConfigIngressMapTableInfoGroup OBJECT-GROUP
    OBJECTS     { gamQosConfigIngressMapIngressMapId,
                  gamQosConfigIngressMapKey,
                  gamQosConfigIngressMapActionCos,
                  gamQosConfigIngressMapActionDpl,
                  gamQosConfigIngressMapActionPcp,
                  gamQosConfigIngressMapActionDei,
                  gamQosConfigIngressMapActionDscp,
                  gamQosConfigIngressMapActionCosid,
                  gamQosConfigIngressMapActionPath,
                  gamQosConfigIngressMapAction }
    STATUS      current
    DESCRIPTION
        "A collection of objects."
    ::= { gamQosMibGroups 27 }

gamQosConfigIngressMapTableRowEditorInfoGroup OBJECT-GROUP
    OBJECTS     { gamQosConfigIngressMapTableRowEditorIngressMapId,
                  gamQosConfigIngressMapTableRowEditorKey,
                  gamQosConfigIngressMapTableRowEditorActionCos,
                  gamQosConfigIngressMapTableRowEditorActionDpl,
                  gamQosConfigIngressMapTableRowEditorActionPcp,
                  gamQosConfigIngressMapTableRowEditorActionDei,
                  gamQosConfigIngressMapTableRowEditorActionDscp,
                  gamQosConfigIngressMapTableRowEditorActionCosid,
                  gamQosConfigIngressMapTableRowEditorActionPath,
                  gamQosConfigIngressMapTableRowEditorAction }
    STATUS      current
    DESCRIPTION
        "A collection of objects."
    ::= { gamQosMibGroups 28 }

gamQosConfigIngressMapPcpTableInfoGroup OBJECT-GROUP
    OBJECTS     { gamQosConfigIngressMapPcpIngressMapId,
                  gamQosConfigIngressMapPcpPcp,
                  gamQosConfigIngressMapPcpDei,
                  gamQosConfigIngressMapPcpToCos,
                  gamQosConfigIngressMapPcpToDpl,
                  gamQosConfigIngressMapPcpToPcp,
                  gamQosConfigIngressMapPcpToDei,
                  gamQosConfigIngressMapPcpToDscp,
                  gamQosConfigIngressMapPcpToCosid,
                  gamQosConfigIngressMapPcpToPathCosid }
    STATUS      current
    DESCRIPTION
        "A collection of objects."
    ::= { gamQosMibGroups 29 }

gamQosConfigIngressMapDscpTableInfoGroup OBJECT-GROUP
    OBJECTS     { gamQosConfigIngressMapDscpIngressMapId,
                  gamQosConfigIngressMapDscpDscp,
                  gamQosConfigIngressMapDscpToCos,
                  gamQosConfigIngressMapDscpToDpl,
                  gamQosConfigIngressMapDscpToPcp,
                  gamQosConfigIngressMapDscpToDei,
                  gamQosConfigIngressMapDscpToDscp,
                  gamQosConfigIngressMapDscpToCosid,
                  gamQosConfigIngressMapDscpToPathCosid }
    STATUS      current
    DESCRIPTION
        "A collection of objects."
    ::= { gamQosMibGroups 30 }

gamQosConfigEgressMapTableInfoGroup OBJECT-GROUP
    OBJECTS     { gamQosConfigEgressMapEgressMapId,
                  gamQosConfigEgressMapKey,
                  gamQosConfigEgressMapActionPcp,
                  gamQosConfigEgressMapActionDei,
                  gamQosConfigEgressMapActionDscp,
                  gamQosConfigEgressMapActionPath,
                  gamQosConfigEgressMapAction }
    STATUS      current
    DESCRIPTION
        "A collection of objects."
    ::= { gamQosMibGroups 31 }

gamQosConfigEgressMapTableRowEditorInfoGroup OBJECT-GROUP
    OBJECTS     { gamQosConfigEgressMapTableRowEditorEgressMapId,
                  gamQosConfigEgressMapTableRowEditorKey,
                  gamQosConfigEgressMapTableRowEditorActionPcp,
                  gamQosConfigEgressMapTableRowEditorActionDei,
                  gamQosConfigEgressMapTableRowEditorActionDscp,
                  gamQosConfigEgressMapTableRowEditorActionPath,
                  gamQosConfigEgressMapTableRowEditorAction }
    STATUS      current
    DESCRIPTION
        "A collection of objects."
    ::= { gamQosMibGroups 32 }

gamQosConfigEgressMapCosidTableInfoGroup OBJECT-GROUP
    OBJECTS     { gamQosConfigEgressMapCosidEgressMapId,
                  gamQosConfigEgressMapCosidCosid,
                  gamQosConfigEgressMapCosidDpl,
                  gamQosConfigEgressMapCosidToPcp,
                  gamQosConfigEgressMapCosidToDei,
                  gamQosConfigEgressMapCosidToDscp,
                  gamQosConfigEgressMapCosidToPathCosid }
    STATUS      current
    DESCRIPTION
        "A collection of objects."
    ::= { gamQosMibGroups 33 }

gamQosConfigEgressMapDscpTableInfoGroup OBJECT-GROUP
    OBJECTS     { gamQosConfigEgressMapDscpEgressMapId,
                  gamQosConfigEgressMapDscpDscp,
                  gamQosConfigEgressMapDscpDpl,
                  gamQosConfigEgressMapDscpToPcp,
                  gamQosConfigEgressMapDscpToDei,
                  gamQosConfigEgressMapDscpToDscp,
                  gamQosConfigEgressMapDscpToPathCosid }
    STATUS      current
    DESCRIPTION
        "A collection of objects."
    ::= { gamQosMibGroups 34 }

gamQosConfigPsfpSfiTableInfoGroup OBJECT-GROUP
    OBJECTS     { gamQosConfigPsfpSfiSfiId,
                  gamQosConfigPsfpSfiStreamHandleSpec,
                  gamQosConfigPsfpSfiPrioritySpec,
                  gamQosConfigPsfpSfiInterfaceSpec,
                  gamQosConfigPsfpSfiStreamGateInstanceId,
                  gamQosConfigPsfpSfiMaximumSduSize,
                  gamQosConfigPsfpSfiFlowMeterInstanceId,
                  gamQosConfigPsfpSfiBlockOversizeEnable,
                  gamQosConfigPsfpSfiBlockOversize,
                  gamQosConfigPsfpSfiAction }
    STATUS      current
    DESCRIPTION
        "A collection of objects."
    ::= { gamQosMibGroups 35 }

gamQosConfigPsfpSfiTableRowEditorInfoGroup OBJECT-GROUP
    OBJECTS     { gamQosConfigPsfpSfiTableRowEditorSfiId,
                  gamQosConfigPsfpSfiTableRowEditorStreamHandleSpec,
                  gamQosConfigPsfpSfiTableRowEditorPrioritySpec,
                  gamQosConfigPsfpSfiTableRowEditorInterfaceSpec,
                  gamQosConfigPsfpSfiTableRowEditorStreamGateInstanceId,
                  gamQosConfigPsfpSfiTableRowEditorMaximumSduSize,
                  gamQosConfigPsfpSfiTableRowEditorFlowMeterInstanceId,
                  gamQosConfigPsfpSfiTableRowEditorBlockOversizeEnable,
                  gamQosConfigPsfpSfiTableRowEditorBlockOversize,
                  gamQosConfigPsfpSfiTableRowEditorAction }
    STATUS      current
    DESCRIPTION
        "A collection of objects."
    ::= { gamQosMibGroups 36 }

gamQosConfigPsfpGclTableInfoGroup OBJECT-GROUP
    OBJECTS     { gamQosConfigPsfpGclSgiId, gamQosConfigPsfpGclGclId,
                  gamQosConfigPsfpGclGateState,
                  gamQosConfigPsfpGclIPV,
                  gamQosConfigPsfpGclTimeInterval,
                  gamQosConfigPsfpGclOctetMax }
    STATUS      current
    DESCRIPTION
        "A collection of objects."
    ::= { gamQosMibGroups 37 }

gamQosConfigPsfpSgiTableInfoGroup OBJECT-GROUP
    OBJECTS     { gamQosConfigPsfpSgiSgiId,
                  gamQosConfigPsfpSgiGateEnabled,
                  gamQosConfigPsfpSgiGateStates,
                  gamQosConfigPsfpSgiListMax,
                  gamQosConfigPsfpSgiCycleTimeNumerator,
                  gamQosConfigPsfpSgiCycleTimeDenominator,
                  gamQosConfigPsfpSgiCycleTimeExtension,
                  gamQosConfigPsfpSgiAdminBaseTimeSecs,
                  gamQosConfigPsfpSgiAdminBaseTimeNanoSecs,
                  gamQosConfigPsfpSgiAdminIPV,
                  gamQosConfigPsfpSgiConfigChange,
                  gamQosConfigPsfpSgiBlockInvalidRxenable,
                  gamQosConfigPsfpSgiBlockInvalidRx,
                  gamQosConfigPsfpSgiAction }
    STATUS      current
    DESCRIPTION
        "A collection of objects."
    ::= { gamQosMibGroups 38 }

gamQosConfigPsfpSgiTableRowEditorInfoGroup OBJECT-GROUP
    OBJECTS     { gamQosConfigPsfpSgiTableRowEditorSgiId,
                  gamQosConfigPsfpSgiTableRowEditorGateEnabled,
                  gamQosConfigPsfpSgiTableRowEditorGateStates,
                  gamQosConfigPsfpSgiTableRowEditorListMax,
                  gamQosConfigPsfpSgiTableRowEditorCycleTimeNumerator,
                  gamQosConfigPsfpSgiTableRowEditorCycleTimeDenominator,
                  gamQosConfigPsfpSgiTableRowEditorCycleTimeExtension,
                  gamQosConfigPsfpSgiTableRowEditorAdminBaseTimeSecs,
                  gamQosConfigPsfpSgiTableRowEditorAdminBaseTimeNanoSecs,
                  gamQosConfigPsfpSgiTableRowEditorAdminIPV,
                  gamQosConfigPsfpSgiTableRowEditorConfigChange,
                  gamQosConfigPsfpSgiTableRowEditorBlockInvalidRxenable,
                  gamQosConfigPsfpSgiTableRowEditorBlockInvalidRx,
                  gamQosConfigPsfpSgiTableRowEditorAction }
    STATUS      current
    DESCRIPTION
        "A collection of objects."
    ::= { gamQosMibGroups 39 }

gamQosConfigPsfpFmiTableInfoGroup OBJECT-GROUP
    OBJECTS     { gamQosConfigPsfpFmiFmiId,
                  gamQosConfigPsfpFmiFlowMeterCIR,
                  gamQosConfigPsfpFmiFlowMeterCBS,
                  gamQosConfigPsfpFmiFlowMeterEIR,
                  gamQosConfigPsfpFmiFlowMeterEBS,
                  gamQosConfigPsfpFmiFlowMeterCF,
                  gamQosConfigPsfpFmiFlowMeterCM,
                  gamQosConfigPsfpFmiFlowMeterDropOnYellow,
                  gamQosConfigPsfpFmiMarkRedEnable,
                  gamQosConfigPsfpFmiMarkRed,
                  gamQosConfigPsfpFmiAction }
    STATUS      current
    DESCRIPTION
        "A collection of objects."
    ::= { gamQosMibGroups 40 }

gamQosConfigPsfpFmiTableRowEditorInfoGroup OBJECT-GROUP
    OBJECTS     { gamQosConfigPsfpFmiTableRowEditorFmiId,
                  gamQosConfigPsfpFmiTableRowEditorFlowMeterCIR,
                  gamQosConfigPsfpFmiTableRowEditorFlowMeterCBS,
                  gamQosConfigPsfpFmiTableRowEditorFlowMeterEIR,
                  gamQosConfigPsfpFmiTableRowEditorFlowMeterEBS,
                  gamQosConfigPsfpFmiTableRowEditorFlowMeterCF,
                  gamQosConfigPsfpFmiTableRowEditorFlowMeterCM,
                  gamQosConfigPsfpFmiTableRowEditorFlowMeterDropOnYellow,
                  gamQosConfigPsfpFmiTableRowEditorMarkRedEnable,
                  gamQosConfigPsfpFmiTableRowEditorMarkRed,
                  gamQosConfigPsfpFmiTableRowEditorAction }
    STATUS      current
    DESCRIPTION
        "A collection of objects."
    ::= { gamQosMibGroups 41 }

gamQosStatusInterfaceTableInfoGroup OBJECT-GROUP
    OBJECTS     { gamQosStatusInterfaceIfIndex,
                  gamQosStatusInterfaceCos }
    STATUS      current
    DESCRIPTION
        "A collection of objects."
    ::= { gamQosMibGroups 42 }

gamQosStatusInterfaceSchedulerTableInfoGroup OBJECT-GROUP
    OBJECTS     { gamQosStatusInterfaceSchedulerIfIndex,
                  gamQosStatusInterfaceSchedulerQueue,
                  gamQosStatusInterfaceSchedulerWeight }
    STATUS      current
    DESCRIPTION
        "A collection of objects."
    ::= { gamQosMibGroups 43 }

gamQosStatusInterfaceQbvGclOprTableInfoGroup OBJECT-GROUP
    OBJECTS     { gamQosStatusInterfaceQbvGclOprIfIndex,
                  gamQosStatusInterfaceQbvGclOprGclIndex,
                  gamQosStatusInterfaceQbvGclOprGateState,
                  gamQosStatusInterfaceQbvGclOprTimeInterval }
    STATUS      current
    DESCRIPTION
        "A collection of objects."
    ::= { gamQosMibGroups 44 }

gamQosStatusInterfaceQbvOprStatusTableInfoGroup OBJECT-GROUP
    OBJECTS     { gamQosStatusInterfaceQbvOprStatusIfIndex,
                  gamQosStatusInterfaceQbvOprStatusOperGateStates,
                  gamQosStatusInterfaceQbvOprStatusOperControlListLength,
                  gamQosStatusInterfaceQbvOprStatusOperCycleTimeNumerator,
                  gamQosStatusInterfaceQbvOprStatusOperCycleTimeDenominator,
                  gamQosStatusInterfaceQbvOprStatusOperCycleTimeExtension,
                  gamQosStatusInterfaceQbvOprStatusOperBaseTimeSecs,
                  gamQosStatusInterfaceQbvOprStatusOperBaseTimeNanoSecs,
                  gamQosStatusInterfaceQbvOprStatusConfigChangeTime,
                  gamQosStatusInterfaceQbvOprStatusTickGranularity,
                  gamQosStatusInterfaceQbvOprStatusCurrentTime,
                  gamQosStatusInterfaceQbvOprStatusConfigPending,
                  gamQosStatusInterfaceQbvOprStatusConfigChangeError,
                  gamQosStatusInterfaceQbvOprStatusSupportedListMax }
    STATUS      current
    DESCRIPTION
        "A collection of objects."
    ::= { gamQosMibGroups 45 }

gamQosStatusInterfaceFpStatusTableInfoGroup OBJECT-GROUP
    OBJECTS     { gamQosStatusInterfaceFpStatusIfIndex,
                  gamQosStatusInterfaceFpStatusHoldAdvance,
                  gamQosStatusInterfaceFpStatusReleaseAdvance,
                  gamQosStatusInterfaceFpStatusPreemptionActive,
                  gamQosStatusInterfaceFpStatusHoldRequest,
                  gamQosStatusInterfaceFpStatusStatusVerify,
                  gamQosStatusInterfaceFpStatusLocPreemptSupported,
                  gamQosStatusInterfaceFpStatusLocPreemptEnabled,
                  gamQosStatusInterfaceFpStatusLocPreemptActive,
                  gamQosStatusInterfaceFpStatusLocAddFragSize }
    STATUS      current
    DESCRIPTION
        "A collection of objects."
    ::= { gamQosMibGroups 46 }

gamQosStatusQceTableInfoGroup OBJECT-GROUP
    OBJECTS     { gamQosStatusQceSwitchId, gamQosStatusQceIndex,
                  gamQosStatusQceUserId, gamQosStatusQceQceId,
                  gamQosStatusQceConflict }
    STATUS      current
    DESCRIPTION
        "A collection of objects."
    ::= { gamQosMibGroups 47 }

gamQosStatusPsfpStreamParametersInfoGroup OBJECT-GROUP
    OBJECTS     {                   gamQosStatusPsfpStreamParametersPsfpStreamFilteringInstanceMax,
                  gamQosStatusPsfpStreamParametersPsfpStreamGateInstanceMax,
                  gamQosStatusPsfpStreamParametersPsfpFlowMeterInstanceMax,
                  gamQosStatusPsfpStreamParametersPsfpAdminControlListMax }
    STATUS      current
    DESCRIPTION
        "A collection of objects."
    ::= { gamQosMibGroups 48 }

gamQosStatusPsfpSfiTableInfoGroup OBJECT-GROUP
    OBJECTS     { gamQosStatusPsfpSfiSfiId,
                  gamQosStatusPsfpSfiMatchingFramesCount,
                  gamQosStatusPsfpSfiPassingFramesCount,
                  gamQosStatusPsfpSfiNotPassingFramesCount,
                  gamQosStatusPsfpSfiPassingSDUCount,
                  gamQosStatusPsfpSfiNotPassingSDUCount,
                  gamQosStatusPsfpSfiREDFramesCount }
    STATUS      current
    DESCRIPTION
        "A collection of objects."
    ::= { gamQosMibGroups 49 }

gamQosStatusPsfpGclTableInfoGroup OBJECT-GROUP
    OBJECTS     { gamQosStatusPsfpGclSgiId, gamQosStatusPsfpGclGclId,
                  gamQosStatusPsfpGclGateState,
                  gamQosStatusPsfpGclIPV,
                  gamQosStatusPsfpGclTimeInterval,
                  gamQosStatusPsfpGclOctetMax }
    STATUS      current
    DESCRIPTION
        "A collection of objects."
    ::= { gamQosMibGroups 50 }

gamQosStatusPsfpSgiTableInfoGroup OBJECT-GROUP
    OBJECTS     { gamQosStatusPsfpSgiSgiId,
                  gamQosStatusPsfpSgiOperGateStates,
                  gamQosStatusPsfpSgiOperControlListLength,
                  gamQosStatusPsfpSgiOperCycleTimeNumerator,
                  gamQosStatusPsfpSgiOperCycleTimeDenominator,
                  gamQosStatusPsfpSgiOperCycleTimeExtension,
                  gamQosStatusPsfpSgiOperBaseTime,
                  gamQosStatusPsfpSgiConfigChangeTime,
                  gamQosStatusPsfpSgiTickGranularity,
                  gamQosStatusPsfpSgiCurrentTime,
                  gamQosStatusPsfpSgiConfigPending,
                  gamQosStatusPsfpSgiConfigChangeError,
                  gamQosStatusPsfpSgiOperIPV }
    STATUS      current
    DESCRIPTION
        "A collection of objects."
    ::= { gamQosMibGroups 51 }

gamQosControlQceInfoGroup OBJECT-GROUP
    OBJECTS     { gamQosControlQceConflictResolve }
    STATUS      current
    DESCRIPTION
        "A collection of objects."
    ::= { gamQosMibGroups 52 }

gamQosControlPsfpSfiCountersInfoGroup OBJECT-GROUP
    OBJECTS     { gamQosControlPsfpSfiCountersSfiId,
                  gamQosControlPsfpSfiCountersClear }
    STATUS      current
    DESCRIPTION
        "A collection of objects."
    ::= { gamQosMibGroups 53 }

gamQosMibCompliance MODULE-COMPLIANCE
    STATUS      current
    DESCRIPTION
        "The compliance statement for the implementation."

    MODULE      -- this module

    MANDATORY-GROUPS { gamQosCapabilitiesInfoGroup,
                       gamQosConfigGlobalsStormPolicersUnicastInfoGroup,
                       gamQosConfigGlobalsStormPolicersMulticastInfoGroup,
                       gamQosConfigGlobalsStormPolicersBroadcastInfoGroup,
                       gamQosConfigGlobalsWredTableInfoGroup,
                       gamQosConfigGlobalsDscpTableInfoGroup,
                       gamQosConfigGlobalsCosToDscpTableInfoGroup,
                       gamQosConfigGlobalsPcpCosMapTableInfoGroup,
                       gamQosConfigInterfaceTableInfoGroup,
                       gamQosConfigInterfaceTagToCosTableInfoGroup,
                       gamQosConfigInterfaceCosToTagTableInfoGroup,
                       gamQosConfigInterfacePolicerTableInfoGroup,
                       gamQosConfigInterfaceQueuePolicerTableInfoGroup,
                       gamQosConfigInterfaceShaperTableInfoGroup,
                       gamQosConfigInterfaceQueueShaperTableInfoGroup,
                       gamQosConfigInterfaceSchedulerTableInfoGroup,
                       gamQosConfigInterfaceStormPolicerUnicastTableInfoGroup,
                       gamQosConfigInterfaceStormPolicerBroadcastTableInfoGroup,
                       gamQosConfigInterfaceStormPolicerUnknownTableInfoGroup,
                       gamQosConfigInterfaceQbvMaxSduTableInfoGroup,
                       gamQosConfigInterfaceQbvGclAdminTableInfoGroup,
                       gamQosConfigInterfaceQbvParamsTableInfoGroup,
                       gamQosConfigInterfaceFpTableInfoGroup,
                       gamQosConfigQceTableInfoGroup,
                       gamQosConfigQceTableRowEditorInfoGroup,
                       gamQosConfigQcePrecedenceTableInfoGroup,
                       gamQosConfigIngressMapTableInfoGroup,
                       gamQosConfigIngressMapTableRowEditorInfoGroup,
                       gamQosConfigIngressMapPcpTableInfoGroup,
                       gamQosConfigIngressMapDscpTableInfoGroup,
                       gamQosConfigEgressMapTableInfoGroup,
                       gamQosConfigEgressMapTableRowEditorInfoGroup,
                       gamQosConfigEgressMapCosidTableInfoGroup,
                       gamQosConfigEgressMapDscpTableInfoGroup,
                       gamQosConfigPsfpSfiTableInfoGroup,
                       gamQosConfigPsfpSfiTableRowEditorInfoGroup,
                       gamQosConfigPsfpGclTableInfoGroup,
                       gamQosConfigPsfpSgiTableInfoGroup,
                       gamQosConfigPsfpSgiTableRowEditorInfoGroup,
                       gamQosConfigPsfpFmiTableInfoGroup,
                       gamQosConfigPsfpFmiTableRowEditorInfoGroup,
                       gamQosStatusInterfaceTableInfoGroup,
                       gamQosStatusInterfaceSchedulerTableInfoGroup,
                       gamQosStatusInterfaceQbvGclOprTableInfoGroup,
                       gamQosStatusInterfaceQbvOprStatusTableInfoGroup,
                       gamQosStatusInterfaceFpStatusTableInfoGroup,
                       gamQosStatusQceTableInfoGroup,
                       gamQosStatusPsfpStreamParametersInfoGroup,
                       gamQosStatusPsfpSfiTableInfoGroup,
                       gamQosStatusPsfpGclTableInfoGroup,
                       gamQosStatusPsfpSgiTableInfoGroup,
                       gamQosControlQceInfoGroup,
                       gamQosControlPsfpSfiCountersInfoGroup }

    ::= { gamQosMibCompliances 1 }

END
