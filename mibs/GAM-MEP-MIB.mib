-- *****************************************************************
-- MEP-MIB:  Positron's GAM private MIB
-- *****************************************************************

GAM-MEP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    GAMDisplayString FROM GAM-TC
    GAMInterfaceIndex FROM GAM-TC
    GAMMepDmTimeUnit FROM GAM-TC
    GAMMepInstanceDirection FROM GAM-TC
    GAMMepTxRate FROM GAM-TC
    GAMRowEditorState FROM GAM-TC
    GAMUnsigned16 FROM GAM-TC
    GAMUnsigned64 FROM GAM-TC
    GAMUnsigned8 FROM GAM-TC
    Counter64 FROM SNMPv2-SMI
    Integer32 FROM SNMPv2-SMI
    IpAddress FROM SNMPv2-SMI
    Unsigned32 FROM SNMPv2-SMI
    MacAddress FROM SNMPv2-TC
    TruthValue FROM SNMPv2-TC
    ;

gamMepMib MODULE-IDENTITY
    LAST-UPDATED "201711150000Z"
    ORGANIZATION
        "Positron Access Solutions Corp."
    CONTACT-INFO
        "Customer Service <info@positronaccess.com>"
    DESCRIPTION
        "This is a private service OAM (Y.1731/G802.1ag/G8113.1/G8113.2) MIB"
    REVISION    "201711150000Z"
    DESCRIPTION
        "Added MyDiscr1 and RemoteDiscr1 objects to MepStatusBfdTable."
    REVISION    "201707070000Z"
    DESCRIPTION
        "Added support for management of Synthetic Loss Measurement (SLM)
         function. Added MepStatusLmPeerTable to provide Loss Measurement status
         for multiple peer MEPs. Added Peer Id index to MepStatusLmAvailTable
         and MepStatusLmHliTable to support multiple peers for SLM. Added
         ElapsedIntervals object to MepStatusLmTable. "
    REVISION    "201706270000Z"
    DESCRIPTION
        "Added option to view DM FD and IFDV bin values in StatusDmFdBinsTable
         and StatusDmIfdvBinsTable."
    REVISION    "201705220000Z"
    DESCRIPTION
        "Changed Mep instance ID numbering convention to start from 1 instead of
         from 0."
    REVISION    "201705190000Z"
    DESCRIPTION
        "Added LM Availability sliding window counters (NearEndWindowCnt and
         FarEndWindowCnt) to mepStatusLmAvailTable."
    REVISION    "201606200000Z"
    DESCRIPTION
        "Added capability element for OAM SW support"
    REVISION    "201509230000Z"
    DESCRIPTION
        "Changed type and description for vtssMepStatusLmNearEndLosCounterInt
         and vtssMepStatusLmFarEndLosCounterInt"
    REVISION    "201508190000Z"
    DESCRIPTION
        "Bugzila 19123 fixed, by updating FD and IFDV get status function"
    REVISION    "201508130000Z"
    DESCRIPTION
        "Added Operational State and more capabilities"
    REVISION    "201508060000Z"
    DESCRIPTION
        "Added FD and IFDV bins for DM"
    REVISION    "201501190000Z"
    DESCRIPTION
        "Added Loss Measurement Availability, High Loss Interval and Signal
         Degrade"
    REVISION    "201501020000Z"
    DESCRIPTION
        "Removed DEI"
    REVISION    "201412030000Z"
    DESCRIPTION
        "Adding Link State Tracking"
    REVISION    "201411260000Z"
    DESCRIPTION
        "Adding Loss Measurement OAM frame counting object"
    REVISION    "201411140000Z"
    DESCRIPTION
        "Refactoring regarding Ifindex. Domain element is removed and flow
         element is changed to be Ifindex containing domain"
    REVISION    "201409300000Z"
    DESCRIPTION
        "Added vtssMepConfigRt and vtssMepStatusRt for Route Trace configuration
         and status"
    REVISION    "201409030000Z"
    DESCRIPTION
        "Added vtssMepConfigClientFlowDomain and vtssMepConfigClientFlowFlowId
         to vtssMepConfigClientFlowTable"
    REVISION    "201407010000Z"
    DESCRIPTION
        "Initial version"
    ::= { gamMgmt 46 }


GAMMepApsType ::= TEXTUAL-CONVENTION
    STATUS      current
    DESCRIPTION
        "Type of APS."
    SYNTAX      INTEGER { invalidAps(0), linearAps(1), ringAps(2) }

GAMMepBfdAuthenticationType ::= TEXTUAL-CONVENTION
    STATUS      current
    DESCRIPTION
        "BFD authentication type."
    SYNTAX      INTEGER { disabled(0), simplePwd(1), keyedMD5(2),
                          meticulousKeyedMD5(3), keyedSHA1(4),
                          meticulousKeyedSHA1(5) }

GAMMepBfdDiagnosticCode ::= TEXTUAL-CONVENTION
    STATUS      current
    DESCRIPTION
        "BFD diagnostic code."
    SYNTAX      INTEGER { none(0), detectExpired(1), echoFailed(2),
                          remoteDown(3), fwdPlaneReset(4),
                          pathDown(5), concatPathDown(6),
                          adminDown(7), reverseConcatDown(8),
                          misconnectivity(9) }

GAMMepBfdSessionState ::= TEXTUAL-CONVENTION
    STATUS      current
    DESCRIPTION
        "State of BFD session."
    SYNTAX      INTEGER { adminDown(0), down(1), init(2), up(3) }

GAMMepCast ::= TEXTUAL-CONVENTION
    STATUS      current
    DESCRIPTION
        "Unicast or Multicast selection."
    SYNTAX      INTEGER { uniCast(0), multiCast(1) }

GAMMepDmCalcWay ::= TEXTUAL-CONVENTION
    STATUS      current
    DESCRIPTION
        "Round trip or flow calculation way selection."
    SYNTAX      INTEGER { roundTrip(0), flow(1) }

GAMMepDmOverflowAction ::= TEXTUAL-CONVENTION
    STATUS      current
    DESCRIPTION
        "Action when internal total delay counter overflow."
    SYNTAX      INTEGER { disableDm(0), continueDm(1) }

GAMMepEnded ::= TEXTUAL-CONVENTION
    STATUS      current
    DESCRIPTION
        "Dual/single ended selection."
    SYNTAX      INTEGER { singleEnded(0), dualEnded(1) }

GAMMepInstanceMode ::= TEXTUAL-CONVENTION
    STATUS      current
    DESCRIPTION
        "The instance mode."
    SYNTAX      INTEGER { mep(0), mip(1) }

GAMMepLmAvailState ::= TEXTUAL-CONVENTION
    STATUS      current
    DESCRIPTION
        "Loss Measurement Availability State."
    SYNTAX      INTEGER { available(0), unavailable(1) }

GAMMepLtRelayAction ::= TEXTUAL-CONVENTION
    STATUS      current
    DESCRIPTION
        "The Link Trace relay action."
    SYNTAX      INTEGER { relayUnknown(0), relayHit(1), relayFdb(2),
                          relayMpdb(3) }

GAMMepMegIdFormat ::= TEXTUAL-CONVENTION
    STATUS      current
    DESCRIPTION
        "The MEG-ID format."
    SYNTAX      INTEGER { ituIcc(0), ieeeString(1), ituCcIcc(2) }

GAMMepOamCount ::= TEXTUAL-CONVENTION
    STATUS      current
    DESCRIPTION
        "Loss Measurement OAM frame counting selection."
    SYNTAX      INTEGER { countAsY1731(0), countNone(1), countAll(2) }

GAMMepOperState ::= TEXTUAL-CONVENTION
    STATUS      current
    DESCRIPTION
        "Instance Operation State."
    SYNTAX      INTEGER { operStateUp(0), operStateDown(1),
                          operStateDownInvalidConf(2),
                          operStateDownfailingOamHw(3),
                          operStateDownfailingMce(4) }

GAMMepRtPadTlvType ::= TEXTUAL-CONVENTION
    STATUS      current
    DESCRIPTION
        "RT Pad TLV type."
    SYNTAX      INTEGER { none(0), drop(1), copy(2) }

GAMMepRtReturnCode ::= TEXTUAL-CONVENTION
    STATUS      current
    DESCRIPTION
        "RT return code type."
    SYNTAX      INTEGER { none(0), malformed(1), tlvError(2),
                          isEgress(3), noMapping(4),
                          downMapMismatch(5), upIfUnknown(6),
                          labelSwitch(8), labelSwitchNoFwd(9),
                          mappingWrong(10), noLabel(11),
                          protocolError(12), premature(13) }

GAMMepTstPattern ::= TEXTUAL-CONVENTION
    STATUS      current
    DESCRIPTION
        "Pattern in TST frame Data TLV."
    SYNTAX      INTEGER { allZero(0), allOne(1), hexAA(2) }

gamMepMibObjects OBJECT IDENTIFIER
    ::= { gamMepMib 1 }

gamMepCapabilities OBJECT IDENTIFIER
    ::= { gamMepMibObjects 1 }

gamMepCapabilitiesInstanceMax OBJECT-TYPE
    SYNTAX      Unsigned32
    MAX-ACCESS  read-only
    STATUS      current
    DESCRIPTION
        "Max number of MEP instance"
    ::= { gamMepCapabilities 1 }

gamMepCapabilitiesPeerMax OBJECT-TYPE
    SYNTAX      Unsigned32
    MAX-ACCESS  read-only
    STATUS      current
    DESCRIPTION
        "Max number of peer MEP"
    ::= { gamMepCapabilities 2 }

gamMepCapabilitiesTransactionMax OBJECT-TYPE
    SYNTAX      Unsigned32
    MAX-ACCESS  read-only
    STATUS      current
    DESCRIPTION
        "Max number of Link Trace transaction"
    ::= { gamMepCapabilities 3 }

gamMepCapabilitiesReplyMax OBJECT-TYPE
    SYNTAX      Unsigned32
    MAX-ACCESS  read-only
    STATUS      current
    DESCRIPTION
        "Max number of reply in a transaction"
    ::= { gamMepCapabilities 4 }

gamMepCapabilitiesClientFlowsMax OBJECT-TYPE
    SYNTAX      Unsigned32
    MAX-ACCESS  read-only
    STATUS      current
    DESCRIPTION
        "Max number of client flows"
    ::= { gamMepCapabilities 5 }

gamMepCapabilitiesMacMength OBJECT-TYPE
    SYNTAX      Unsigned32
    MAX-ACCESS  read-only
    STATUS      current
    DESCRIPTION
        "MAC length"
    ::= { gamMepCapabilities 6 }

gamMepCapabilitiesMegCodeLength OBJECT-TYPE
    SYNTAX      Unsigned32
    MAX-ACCESS  read-only
    STATUS      current
    DESCRIPTION
        "MAX length of Both Maintenance Domain Name and MEG-ID include a NULL
         termination"
    ::= { gamMepCapabilities 7 }

gamMepCapabilitiesDmIntervalMin OBJECT-TYPE
    SYNTAX      Unsigned32
    MAX-ACCESS  read-only
    STATUS      current
    DESCRIPTION
        "MIN DM transmission interval "
    ::= { gamMepCapabilities 8 }

gamMepCapabilitiesDmIntervalMax OBJECT-TYPE
    SYNTAX      Unsigned32
    MAX-ACCESS  read-only
    STATUS      current
    DESCRIPTION
        "MAX DM transmission interval"
    ::= { gamMepCapabilities 9 }

gamMepCapabilitiesDmLastnMin OBJECT-TYPE
    SYNTAX      Unsigned32
    MAX-ACCESS  read-only
    STATUS      current
    DESCRIPTION
        "MIN number of DM LastN for average calculation"
    ::= { gamMepCapabilities 10 }

gamMepCapabilitiesDmLastnMax OBJECT-TYPE
    SYNTAX      Unsigned32
    MAX-ACCESS  read-only
    STATUS      current
    DESCRIPTION
        "MAX number of DM LastN for average calculation"
    ::= { gamMepCapabilities 11 }

gamMepCapabilitiesLbmSizeMax OBJECT-TYPE
    SYNTAX      Unsigned32
    MAX-ACCESS  read-only
    STATUS      current
    DESCRIPTION
        "The maximum LBM frame size"
    ::= { gamMepCapabilities 12 }

gamMepCapabilitiesLbmSizeMin OBJECT-TYPE
    SYNTAX      Unsigned32
    MAX-ACCESS  read-only
    STATUS      current
    DESCRIPTION
        "The minimum LBM frame size"
    ::= { gamMepCapabilities 13 }

gamMepCapabilitiesTstSizeMax OBJECT-TYPE
    SYNTAX      Unsigned32
    MAX-ACCESS  read-only
    STATUS      current
    DESCRIPTION
        "The maximum TST frame size"
    ::= { gamMepCapabilities 14 }

gamMepCapabilitiesTstSizeMin OBJECT-TYPE
    SYNTAX      Unsigned32
    MAX-ACCESS  read-only
    STATUS      current
    DESCRIPTION
        "The minimum TST frame size"
    ::= { gamMepCapabilities 15 }

gamMepCapabilitiesTstRateMax OBJECT-TYPE
    SYNTAX      Unsigned32
    MAX-ACCESS  read-only
    STATUS      current
    DESCRIPTION
        "The maximum TST bit rate"
    ::= { gamMepCapabilities 16 }

gamMepCapabilitiesClientPrioHighest OBJECT-TYPE
    SYNTAX      Unsigned32
    MAX-ACCESS  read-only
    STATUS      current
    DESCRIPTION
        "The highest possible client priority is requested"
    ::= { gamMepCapabilities 17 }

gamMepCapabilitiesItuG8113dot2 OBJECT-TYPE
    SYNTAX      TruthValue
    MAX-ACCESS  read-only
    STATUS      current
    DESCRIPTION
        "Indicates if ITU G8113.2 is supported on this system"
    ::= { gamMepCapabilities 18 }

gamMepCapabilitiesVoeSupport OBJECT-TYPE
    SYNTAX      TruthValue
    MAX-ACCESS  read-only
    STATUS      current
    DESCRIPTION
        "Indicates if HW based OAM engine is supported on this system"
    ::= { gamMepCapabilities 19 }

gamMepCapabilitiesLbToSendInfinite OBJECT-TYPE
    SYNTAX      Unsigned32
    MAX-ACCESS  read-only
    STATUS      current
    DESCRIPTION
        "Send LBM infinite - test behaviour"
    ::= { gamMepCapabilities 20 }

gamMepCapabilitiesBfdAuthKeyMax OBJECT-TYPE
    SYNTAX      Unsigned32
    MAX-ACCESS  read-only
    STATUS      current
    DESCRIPTION
        "Maximum number of BFD authentication keys"
    ::= { gamMepCapabilities 21 }

gamMepCapabilitiesHasEvcPag OBJECT-TYPE
    SYNTAX      TruthValue
    MAX-ACCESS  read-only
    STATUS      current
    DESCRIPTION
        "Indicates if EVC generated policy PAG value as IS2 key is supported on
         this system"
    ::= { gamMepCapabilities 22 }

gamMepCapabilitiesHasEvcQos OBJECT-TYPE
    SYNTAX      TruthValue
    MAX-ACCESS  read-only
    STATUS      current
    DESCRIPTION
        "Indicates if EVC QoS value used for getting queue frame LM counters is
         supported on this system"
    ::= { gamMepCapabilities 23 }

gamMepCapabilitiesHasFlowCount OBJECT-TYPE
    SYNTAX      TruthValue
    MAX-ACCESS  read-only
    STATUS      current
    DESCRIPTION
        "Indicates if Traffic (service frames) counted per flow is supported on
         this system"
    ::= { gamMepCapabilities 24 }

gamMepCapabilitiesHasOamCount OBJECT-TYPE
    SYNTAX      TruthValue
    MAX-ACCESS  read-only
    STATUS      current
    DESCRIPTION
        "Indicates if Loss Measurement count of OAM frames in different ways is
         supported on this system"
    ::= { gamMepCapabilities 25 }

gamMepCapabilitiesHasOperState OBJECT-TYPE
    SYNTAX      TruthValue
    MAX-ACCESS  read-only
    STATUS      current
    DESCRIPTION
        "Indicates if instance operational state is supported on this system"
    ::= { gamMepCapabilities 26 }

gamMepCapabilitiesHasOamSwSupport OBJECT-TYPE
    SYNTAX      TruthValue
    MAX-ACCESS  read-only
    STATUS      current
    DESCRIPTION
        "Indicates if SW based OAM engine is supported on this system"
    ::= { gamMepCapabilities 27 }

gamMepConfig OBJECT IDENTIFIER
    ::= { gamMepMibObjects 2 }

gamMepConfigInstance OBJECT IDENTIFIER
    ::= { gamMepConfig 1 }

gamMepConfigInstanceTable OBJECT-TYPE
    SYNTAX      SEQUENCE OF GAMMepConfigInstanceEntry
    MAX-ACCESS  not-accessible
    STATUS      current
    DESCRIPTION
        "This is a table of created instance configuration parameters"
    ::= { gamMepConfigInstance 1 }

gamMepConfigInstanceEntry OBJECT-TYPE
    SYNTAX      GAMMepConfigInstanceEntry
    MAX-ACCESS  not-accessible
    STATUS      current
    DESCRIPTION
        "This is a created instance configuration parameters. Not all parameters
         can be changed"
    INDEX       { gamMepConfigInstanceId }
    ::= { gamMepConfigInstanceTable 1 }

GAMMepConfigInstanceEntry ::= SEQUENCE {
    gamMepConfigInstanceId         Integer32,
    gamMepConfigInstanceMode       GAMMepInstanceMode,
    gamMepConfigInstanceDirection  GAMMepInstanceDirection,
    gamMepConfigInstanceFlow       GAMInterfaceIndex,
    gamMepConfigInstancePort       GAMInterfaceIndex,
    gamMepConfigInstanceLevel      Unsigned32,
    gamMepConfigInstanceVid        GAMUnsigned16,
    gamMepConfigInstanceVoe        TruthValue,
    gamMepConfigInstanceMac        MacAddress,
    gamMepConfigInstanceFormat     GAMMepMegIdFormat,
    gamMepConfigInstanceName       GAMDisplayString,
    gamMepConfigInstanceMeg        GAMDisplayString,
    gamMepConfigInstanceMep        Unsigned32,
    gamMepConfigInstanceEvcPag     Unsigned32,
    gamMepConfigInstanceEvcQos     Unsigned32,
    gamMepConfigInstanceAction     GAMRowEditorState
}

gamMepConfigInstanceId OBJECT-TYPE
    SYNTAX      Integer32 (1..2147483647)
    MAX-ACCESS  accessible-for-notify
    STATUS      current
    DESCRIPTION
        "The MEP instance ID"
    ::= { gamMepConfigInstanceEntry 1 }

gamMepConfigInstanceMode OBJECT-TYPE
    SYNTAX      GAMMepInstanceMode
    MAX-ACCESS  read-write
    STATUS      current
    DESCRIPTION
        "The instance mode. Cannot be changed after creation."
    ::= { gamMepConfigInstanceEntry 2 }

gamMepConfigInstanceDirection OBJECT-TYPE
    SYNTAX      GAMMepInstanceDirection
    MAX-ACCESS  read-write
    STATUS      current
    DESCRIPTION
        "The instance direction. Cannot be changed after creation."
    ::= { gamMepConfigInstanceEntry 3 }

gamMepConfigInstanceFlow OBJECT-TYPE
    SYNTAX      GAMInterfaceIndex
    MAX-ACCESS  read-write
    STATUS      current
    DESCRIPTION
        "The flow instance (VLAN - EVC). Cannot be changed after creation."
    ::= { gamMepConfigInstanceEntry 4 }

gamMepConfigInstancePort OBJECT-TYPE
    SYNTAX      GAMInterfaceIndex
    MAX-ACCESS  read-write
    STATUS      current
    DESCRIPTION
        "The instance residence port. Cannot be changed after creation."
    ::= { gamMepConfigInstanceEntry 5 }

gamMepConfigInstanceLevel OBJECT-TYPE
    SYNTAX      Unsigned32
    MAX-ACCESS  read-write
    STATUS      current
    DESCRIPTION
        "The instance level"
    ::= { gamMepConfigInstanceEntry 6 }

gamMepConfigInstanceVid OBJECT-TYPE
    SYNTAX      GAMUnsigned16
    MAX-ACCESS  read-write
    STATUS      current
    DESCRIPTION
        "VID used for tagged Port domain OAM. Create a VLAN MEP instead - if
         possible"
    ::= { gamMepConfigInstanceEntry 7 }

gamMepConfigInstanceVoe OBJECT-TYPE
    SYNTAX      TruthValue
    MAX-ACCESS  read-write
    STATUS      current
    DESCRIPTION
        "Make the instance VOE based - if possible"
    ::= { gamMepConfigInstanceEntry 8 }

gamMepConfigInstanceMac OBJECT-TYPE
    SYNTAX      MacAddress
    MAX-ACCESS  read-write
    STATUS      current
    DESCRIPTION
        "The instance unicast MAC. If 'all zero' the residence port MAC is used"
    ::= { gamMepConfigInstanceEntry 9 }

gamMepConfigInstanceFormat OBJECT-TYPE
    SYNTAX      GAMMepMegIdFormat
    MAX-ACCESS  read-write
    STATUS      current
    DESCRIPTION
        "The MEG-ID format"
    ::= { gamMepConfigInstanceEntry 10 }

gamMepConfigInstanceName OBJECT-TYPE
    SYNTAX      GAMDisplayString (SIZE(0..16))
    MAX-ACCESS  read-write
    STATUS      current
    DESCRIPTION
        "IEEE Maintenance Domain Name (string)"
    ::= { gamMepConfigInstanceEntry 11 }

gamMepConfigInstanceMeg OBJECT-TYPE
    SYNTAX      GAMDisplayString (SIZE(0..16))
    MAX-ACCESS  read-write
    STATUS      current
    DESCRIPTION
        "Unique MEG ID (string)"
    ::= { gamMepConfigInstanceEntry 12 }

gamMepConfigInstanceMep OBJECT-TYPE
    SYNTAX      Unsigned32
    MAX-ACCESS  read-write
    STATUS      current
    DESCRIPTION
        "MEP id of this instance"
    ::= { gamMepConfigInstanceEntry 13 }

gamMepConfigInstanceEvcPag OBJECT-TYPE
    SYNTAX      Unsigned32
    MAX-ACCESS  read-write
    STATUS      current
    DESCRIPTION
        "EVC generated policy PAG value. This is used as IS2 key"
    ::= { gamMepConfigInstanceEntry 14 }

gamMepConfigInstanceEvcQos OBJECT-TYPE
    SYNTAX      Unsigned32
    MAX-ACCESS  read-write
    STATUS      current
    DESCRIPTION
        "EVC QoS value. Used for getting queue frame LM counters."
    ::= { gamMepConfigInstanceEntry 15 }

gamMepConfigInstanceAction OBJECT-TYPE
    SYNTAX      GAMRowEditorState
    MAX-ACCESS  read-write
    STATUS      current
    DESCRIPTION
        "Action"
    ::= { gamMepConfigInstanceEntry 100 }

gamMepConfigInstanceRowEditor OBJECT IDENTIFIER
    ::= { gamMepConfigInstance 2 }

gamMepConfigInstanceRowEditorId OBJECT-TYPE
    SYNTAX      Integer32 (1..2147483647)
    MAX-ACCESS  read-write
    STATUS      current
    DESCRIPTION
        "The MEP instance ID"
    ::= { gamMepConfigInstanceRowEditor 1 }

gamMepConfigInstanceRowEditorMode OBJECT-TYPE
    SYNTAX      GAMMepInstanceMode
    MAX-ACCESS  read-write
    STATUS      current
    DESCRIPTION
        "The instance mode. Cannot be changed after creation."
    ::= { gamMepConfigInstanceRowEditor 2 }

gamMepConfigInstanceRowEditorDirection OBJECT-TYPE
    SYNTAX      GAMMepInstanceDirection
    MAX-ACCESS  read-write
    STATUS      current
    DESCRIPTION
        "The instance direction. Cannot be changed after creation."
    ::= { gamMepConfigInstanceRowEditor 3 }

gamMepConfigInstanceRowEditorFlow OBJECT-TYPE
    SYNTAX      GAMInterfaceIndex
    MAX-ACCESS  read-write
    STATUS      current
    DESCRIPTION
        "The flow instance (VLAN - EVC). Cannot be changed after creation."
    ::= { gamMepConfigInstanceRowEditor 4 }

gamMepConfigInstanceRowEditorPort OBJECT-TYPE
    SYNTAX      GAMInterfaceIndex
    MAX-ACCESS  read-write
    STATUS      current
    DESCRIPTION
        "The instance residence port. Cannot be changed after creation."
    ::= { gamMepConfigInstanceRowEditor 5 }

gamMepConfigInstanceRowEditorLevel OBJECT-TYPE
    SYNTAX      Unsigned32
    MAX-ACCESS  read-write
    STATUS      current
    DESCRIPTION
        "The instance level"
    ::= { gamMepConfigInstanceRowEditor 6 }

gamMepConfigInstanceRowEditorVid OBJECT-TYPE
    SYNTAX      GAMUnsigned16
    MAX-ACCESS  read-write
    STATUS      current
    DESCRIPTION
        "VID used for tagged Port domain OAM. Create a VLAN MEP instead - if
         possible"
    ::= { gamMepConfigInstanceRowEditor 7 }

gamMepConfigInstanceRowEditorVoe OBJECT-TYPE
    SYNTAX      TruthValue
    MAX-ACCESS  read-write
    STATUS      current
    DESCRIPTION
        "Make the instance VOE based - if possible"
    ::= { gamMepConfigInstanceRowEditor 8 }

gamMepConfigInstanceRowEditorMac OBJECT-TYPE
    SYNTAX      MacAddress
    MAX-ACCESS  read-write
    STATUS      current
    DESCRIPTION
        "The instance unicast MAC. If 'all zero' the residence port MAC is used"
    ::= { gamMepConfigInstanceRowEditor 9 }

gamMepConfigInstanceRowEditorFormat OBJECT-TYPE
    SYNTAX      GAMMepMegIdFormat
    MAX-ACCESS  read-write
    STATUS      current
    DESCRIPTION
        "The MEG-ID format"
    ::= { gamMepConfigInstanceRowEditor 10 }

gamMepConfigInstanceRowEditorName OBJECT-TYPE
    SYNTAX      GAMDisplayString (SIZE(0..16))
    MAX-ACCESS  read-write
    STATUS      current
    DESCRIPTION
        "IEEE Maintenance Domain Name (string)"
    ::= { gamMepConfigInstanceRowEditor 11 }

gamMepConfigInstanceRowEditorMeg OBJECT-TYPE
    SYNTAX      GAMDisplayString (SIZE(0..16))
    MAX-ACCESS  read-write
    STATUS      current
    DESCRIPTION
        "Unique MEG ID (string)"
    ::= { gamMepConfigInstanceRowEditor 12 }

gamMepConfigInstanceRowEditorMep OBJECT-TYPE
    SYNTAX      Unsigned32
    MAX-ACCESS  read-write
    STATUS      current
    DESCRIPTION
        "MEP id of this instance"
    ::= { gamMepConfigInstanceRowEditor 13 }

gamMepConfigInstanceRowEditorEvcPag OBJECT-TYPE
    SYNTAX      Unsigned32
    MAX-ACCESS  read-write
    STATUS      current
    DESCRIPTION
        "EVC generated policy PAG value. This is used as IS2 key"
    ::= { gamMepConfigInstanceRowEditor 14 }

gamMepConfigInstanceRowEditorEvcQos OBJECT-TYPE
    SYNTAX      Unsigned32
    MAX-ACCESS  read-write
    STATUS      current
    DESCRIPTION
        "EVC QoS value. Used for getting queue frame LM counters."
    ::= { gamMepConfigInstanceRowEditor 15 }

gamMepConfigInstanceRowEditorAction OBJECT-TYPE
    SYNTAX      GAMRowEditorState
    MAX-ACCESS  read-write
    STATUS      current
    DESCRIPTION
        "Action"
    ::= { gamMepConfigInstanceRowEditor 100 }

gamMepConfigInstancePeerTable OBJECT-TYPE
    SYNTAX      SEQUENCE OF GAMMepConfigInstancePeerEntry
    MAX-ACCESS  not-accessible
    STATUS      current
    DESCRIPTION
        "This is a table of peer MEP configuration parameters"
    ::= { gamMepConfigInstance 3 }

gamMepConfigInstancePeerEntry OBJECT-TYPE
    SYNTAX      GAMMepConfigInstancePeerEntry
    MAX-ACCESS  not-accessible
    STATUS      current
    DESCRIPTION
        "This is a peer MEP configuration parameters"
    INDEX       { gamMepConfigInstancePeerId,
                  gamMepConfigInstancePeerPeerId }
    ::= { gamMepConfigInstancePeerTable 1 }

GAMMepConfigInstancePeerEntry ::= SEQUENCE {
    gamMepConfigInstancePeerId      Integer32,
    gamMepConfigInstancePeerPeerId  Integer32,
    gamMepConfigInstancePeerMac     MacAddress,
    gamMepConfigInstancePeerAction  GAMRowEditorState
}

gamMepConfigInstancePeerId OBJECT-TYPE
    SYNTAX      Integer32 (1..2147483647)
    MAX-ACCESS  accessible-for-notify
    STATUS      current
    DESCRIPTION
        "The MEP instance ID"
    ::= { gamMepConfigInstancePeerEntry 1 }

gamMepConfigInstancePeerPeerId OBJECT-TYPE
    SYNTAX      Integer32 (0..2147483647)
    MAX-ACCESS  accessible-for-notify
    STATUS      current
    DESCRIPTION
        "The Peer MEP ID"
    ::= { gamMepConfigInstancePeerEntry 2 }

gamMepConfigInstancePeerMac OBJECT-TYPE
    SYNTAX      MacAddress
    MAX-ACCESS  read-write
    STATUS      current
    DESCRIPTION
        "The peer unicast MAC"
    ::= { gamMepConfigInstancePeerEntry 3 }

gamMepConfigInstancePeerAction OBJECT-TYPE
    SYNTAX      GAMRowEditorState
    MAX-ACCESS  read-write
    STATUS      current
    DESCRIPTION
        "Action"
    ::= { gamMepConfigInstancePeerEntry 100 }

gamMepConfigInstancePeerRowEditor OBJECT IDENTIFIER
    ::= { gamMepConfigInstance 4 }

gamMepConfigInstancePeerRowEditorId OBJECT-TYPE
    SYNTAX      Integer32 (1..2147483647)
    MAX-ACCESS  read-write
    STATUS      current
    DESCRIPTION
        "The MEP instance ID"
    ::= { gamMepConfigInstancePeerRowEditor 1 }

gamMepConfigInstancePeerRowEditorPeerId OBJECT-TYPE
    SYNTAX      Integer32 (0..2147483647)
    MAX-ACCESS  read-write
    STATUS      current
    DESCRIPTION
        "The Peer MEP ID"
    ::= { gamMepConfigInstancePeerRowEditor 2 }

gamMepConfigInstancePeerRowEditorMac OBJECT-TYPE
    SYNTAX      MacAddress
    MAX-ACCESS  read-write
    STATUS      current
    DESCRIPTION
        "The peer unicast MAC"
    ::= { gamMepConfigInstancePeerRowEditor 3 }

gamMepConfigInstancePeerRowEditorAction OBJECT-TYPE
    SYNTAX      GAMRowEditorState
    MAX-ACCESS  read-write
    STATUS      current
    DESCRIPTION
        "Action"
    ::= { gamMepConfigInstancePeerRowEditor 100 }

gamMepConfigPm OBJECT IDENTIFIER
    ::= { gamMepConfig 2 }

gamMepConfigPmTable OBJECT-TYPE
    SYNTAX      SEQUENCE OF GAMMepConfigPmEntry
    MAX-ACCESS  not-accessible
    STATUS      current
    DESCRIPTION
        "This is a table of created instance Performance Monitoring
         configuration parameters"
    ::= { gamMepConfigPm 1 }

gamMepConfigPmEntry OBJECT-TYPE
    SYNTAX      GAMMepConfigPmEntry
    MAX-ACCESS  not-accessible
    STATUS      current
    DESCRIPTION
        "This is a created instance Performance Monitoring configuration
         parameters"
    INDEX       { gamMepConfigPmId }
    ::= { gamMepConfigPmTable 1 }

GAMMepConfigPmEntry ::= SEQUENCE {
    gamMepConfigPmId      Integer32,
    gamMepConfigPmEnable  TruthValue
}

gamMepConfigPmId OBJECT-TYPE
    SYNTAX      Integer32 (1..2147483647)
    MAX-ACCESS  accessible-for-notify
    STATUS      current
    DESCRIPTION
        "The MEP instance ID"
    ::= { gamMepConfigPmEntry 1 }

gamMepConfigPmEnable OBJECT-TYPE
    SYNTAX      TruthValue
    MAX-ACCESS  read-write
    STATUS      current
    DESCRIPTION
        "The instance can enable contribution of LM and DM results to the
         Performance Monitoring "
    ::= { gamMepConfigPmEntry 2 }

gamMepConfigCc OBJECT IDENTIFIER
    ::= { gamMepConfig 3 }

gamMepConfigCcTable OBJECT-TYPE
    SYNTAX      SEQUENCE OF GAMMepConfigCcEntry
    MAX-ACCESS  not-accessible
    STATUS      current
    DESCRIPTION
        "This is a table of created instance Continuity Check configuration
         parameters"
    ::= { gamMepConfigCc 1 }

gamMepConfigCcEntry OBJECT-TYPE
    SYNTAX      GAMMepConfigCcEntry
    MAX-ACCESS  not-accessible
    STATUS      current
    DESCRIPTION
        "This is a created instance Continuity Check configuration parameters."
    INDEX       { gamMepConfigCcId }
    ::= { gamMepConfigCcTable 1 }

GAMMepConfigCcEntry ::= SEQUENCE {
    gamMepConfigCcId      Integer32,
    gamMepConfigCcPrio    Unsigned32,
    gamMepConfigCcRate    GAMMepTxRate,
    gamMepConfigCcTlv     TruthValue,
    gamMepConfigCcAction  GAMRowEditorState
}

gamMepConfigCcId OBJECT-TYPE
    SYNTAX      Integer32 (1..2147483647)
    MAX-ACCESS  accessible-for-notify
    STATUS      current
    DESCRIPTION
        "The MEP instance ID"
    ::= { gamMepConfigCcEntry 1 }

gamMepConfigCcPrio OBJECT-TYPE
    SYNTAX      Unsigned32
    MAX-ACCESS  read-write
    STATUS      current
    DESCRIPTION
        "Priority of the transmitted CCM. Range 0 to 7"
    ::= { gamMepConfigCcEntry 3 }

gamMepConfigCcRate OBJECT-TYPE
    SYNTAX      GAMMepTxRate
    MAX-ACCESS  read-write
    STATUS      current
    DESCRIPTION
        "CCM transmission and expected reception rate"
    ::= { gamMepConfigCcEntry 4 }

gamMepConfigCcTlv OBJECT-TYPE
    SYNTAX      TruthValue
    MAX-ACCESS  read-write
    STATUS      current
    DESCRIPTION
        "Enable/disable insertion of TLV in CCM PDU. OS, PS and IS TLV are
         inserted"
    ::= { gamMepConfigCcEntry 5 }

gamMepConfigCcAction OBJECT-TYPE
    SYNTAX      GAMRowEditorState
    MAX-ACCESS  read-write
    STATUS      current
    DESCRIPTION
        "Action"
    ::= { gamMepConfigCcEntry 100 }

gamMepConfigCcRowEditor OBJECT IDENTIFIER
    ::= { gamMepConfigCc 2 }

gamMepConfigCcRowEditorId OBJECT-TYPE
    SYNTAX      Integer32 (1..2147483647)
    MAX-ACCESS  read-write
    STATUS      current
    DESCRIPTION
        "The MEP instance ID"
    ::= { gamMepConfigCcRowEditor 1 }

gamMepConfigCcRowEditorPrio OBJECT-TYPE
    SYNTAX      Unsigned32
    MAX-ACCESS  read-write
    STATUS      current
    DESCRIPTION
        "Priority of the transmitted CCM. Range 0 to 7"
    ::= { gamMepConfigCcRowEditor 3 }

gamMepConfigCcRowEditorRate OBJECT-TYPE
    SYNTAX      GAMMepTxRate
    MAX-ACCESS  read-write
    STATUS      current
    DESCRIPTION
        "CCM transmission and expected reception rate"
    ::= { gamMepConfigCcRowEditor 4 }

gamMepConfigCcRowEditorTlv OBJECT-TYPE
    SYNTAX      TruthValue
    MAX-ACCESS  read-write
    STATUS      current
    DESCRIPTION
        "Enable/disable insertion of TLV in CCM PDU. OS, PS and IS TLV are
         inserted"
    ::= { gamMepConfigCcRowEditor 5 }

gamMepConfigCcRowEditorAction OBJECT-TYPE
    SYNTAX      GAMRowEditorState
    MAX-ACCESS  read-write
    STATUS      current
    DESCRIPTION
        "Action"
    ::= { gamMepConfigCcRowEditor 100 }

gamMepConfigLm OBJECT IDENTIFIER
    ::= { gamMepConfig 4 }

gamMepConfigLmTable OBJECT-TYPE
    SYNTAX      SEQUENCE OF GAMMepConfigLmEntry
    MAX-ACCESS  not-accessible
    STATUS      current
    DESCRIPTION
        "This is a table of created instance Loss Measurement configuration
         parameters"
    ::= { gamMepConfigLm 1 }

gamMepConfigLmEntry OBJECT-TYPE
    SYNTAX      GAMMepConfigLmEntry
    MAX-ACCESS  not-accessible
    STATUS      current
    DESCRIPTION
        "This is a created instance Loss Measurement parameters."
    INDEX       { gamMepConfigLmId }
    ::= { gamMepConfigLmTable 1 }

GAMMepConfigLmEntry ::= SEQUENCE {
    gamMepConfigLmId                           Integer32,
    gamMepConfigLmEnable                       TruthValue,
    gamMepConfigLmEnded                        GAMMepEnded,
    gamMepConfigLmPrio                         Unsigned32,
    gamMepConfigLmRate                         GAMMepTxRate,
    gamMepConfigLmCast                         GAMMepCast,
    gamMepConfigLmFlrInterval                  Unsigned32,
    gamMepConfigLmFlowCount                    TruthValue,
    gamMepConfigLmOamCount                     GAMMepOamCount,
    gamMepConfigLmLossTh                       Unsigned32,
    gamMepConfigLmLossCounterIntHolddownTimer  Unsigned32,
    gamMepConfigLmLossThCntHolddownTimer       Unsigned32,
    gamMepConfigLmRxEnable                     TruthValue,
    gamMepConfigLmSynthetic                    TruthValue,
    gamMepConfigLmMep                          Unsigned32,
    gamMepConfigLmFrameSize                    Unsigned32,
    gamMepConfigLmMeasInterval                 Unsigned32,
    gamMepConfigLmSlmTestId                    Unsigned32
}

gamMepConfigLmId OBJECT-TYPE
    SYNTAX      Integer32 (1..2147483647)
    MAX-ACCESS  accessible-for-notify
    STATUS      current
    DESCRIPTION
        "The MEP instance ID"
    ::= { gamMepConfigLmEntry 1 }

gamMepConfigLmEnable OBJECT-TYPE
    SYNTAX      TruthValue
    MAX-ACCESS  read-write
    STATUS      current
    DESCRIPTION
        "Loss Measurement is enabled"
    ::= { gamMepConfigLmEntry 2 }

gamMepConfigLmEnded OBJECT-TYPE
    SYNTAX      GAMMepEnded
    MAX-ACCESS  read-write
    STATUS      current
    DESCRIPTION
        "Dual/single ended selection. CCM or LMM/LMR based. Cannot be changed
         after creation."
    ::= { gamMepConfigLmEntry 3 }

gamMepConfigLmPrio OBJECT-TYPE
    SYNTAX      Unsigned32
    MAX-ACCESS  read-write
    STATUS      current
    DESCRIPTION
        "Priority of the transmitted LM PDU. Range 0 to 7"
    ::= { gamMepConfigLmEntry 5 }

gamMepConfigLmRate OBJECT-TYPE
    SYNTAX      GAMMepTxRate
    MAX-ACCESS  read-write
    STATUS      current
    DESCRIPTION
        "LM PDU transmission rate"
    ::= { gamMepConfigLmEntry 6 }

gamMepConfigLmCast OBJECT-TYPE
    SYNTAX      GAMMepCast
    MAX-ACCESS  read-write
    STATUS      current
    DESCRIPTION
        "Uni/Multicast selection - on CCM based LM only multicast is possible"
    ::= { gamMepConfigLmEntry 7 }

gamMepConfigLmFlrInterval OBJECT-TYPE
    SYNTAX      Unsigned32
    MAX-ACCESS  read-write
    STATUS      current
    DESCRIPTION
        "Frame loss ratio interval in number of measurements."
    ::= { gamMepConfigLmEntry 8 }

gamMepConfigLmFlowCount OBJECT-TYPE
    SYNTAX      TruthValue
    MAX-ACCESS  read-write
    STATUS      current
    DESCRIPTION
        "Traffic (service frames) are counted per flow - all priority in one"
    ::= { gamMepConfigLmEntry 9 }

gamMepConfigLmOamCount OBJECT-TYPE
    SYNTAX      GAMMepOamCount
    MAX-ACCESS  read-write
    STATUS      current
    DESCRIPTION
        "Loss Measurement can count OAM frames in different ways."
    ::= { gamMepConfigLmEntry 10 }

gamMepConfigLmLossTh OBJECT-TYPE
    SYNTAX      Unsigned32
    MAX-ACCESS  read-write
    STATUS      current
    DESCRIPTION
        "Frame loss threshold. The loss threshold count NearEndLosThCnt /
         FarEndLosThCnt is incremented if a loss measurement is above this
         threshold."
    ::= { gamMepConfigLmEntry 11 }

gamMepConfigLmLossCounterIntHolddownTimer OBJECT-TYPE
    SYNTAX      Unsigned32
    MAX-ACCESS  read-write
    STATUS      current
    DESCRIPTION
        "Holddown timer in seconds for JSON notification updates for
         NearEndLosCounterInt and FarEndLosCounterInt."
    ::= { gamMepConfigLmEntry 12 }

gamMepConfigLmLossThCntHolddownTimer OBJECT-TYPE
    SYNTAX      Unsigned32
    MAX-ACCESS  read-write
    STATUS      current
    DESCRIPTION
        "Holddown timer in seconds for JSON notification updates for
         NearEndLosThCnt and FarEndLosThCnt."
    ::= { gamMepConfigLmEntry 13 }

gamMepConfigLmRxEnable OBJECT-TYPE
    SYNTAX      TruthValue
    MAX-ACCESS  read-write
    STATUS      current
    DESCRIPTION
        "This enables calculation of far-to-near loss when CCM/LMM/SLM/1SL is
         received. Can only be set TRUE when 'enable' is FALSE"
    ::= { gamMepConfigLmEntry 14 }

gamMepConfigLmSynthetic OBJECT-TYPE
    SYNTAX      TruthValue
    MAX-ACCESS  read-write
    STATUS      current
    DESCRIPTION
        "TRUE => LM based on synthetic frames (SLM/1SL). FALSE => LM based on
         service frames (LMM/CCM)."
    ::= { gamMepConfigLmEntry 15 }

gamMepConfigLmMep OBJECT-TYPE
    SYNTAX      Unsigned32
    MAX-ACCESS  read-write
    STATUS      current
    DESCRIPTION
        "Peer Mep to receive LM - only used if unicast. Value >
         VTSS_APPL_MEP_ID_MAX can be used when only one peer-mep (default)."
    ::= { gamMepConfigLmEntry 16 }

gamMepConfigLmFrameSize OBJECT-TYPE
    SYNTAX      Unsigned32
    MAX-ACCESS  read-write
    STATUS      current
    DESCRIPTION
        "Size of SLM/1SL frame to send."
    ::= { gamMepConfigLmEntry 17 }

gamMepConfigLmMeasInterval OBJECT-TYPE
    SYNTAX      Unsigned32
    MAX-ACCESS  read-write
    STATUS      current
    DESCRIPTION
        "Synthetic LM measurement interval."
    ::= { gamMepConfigLmEntry 18 }

gamMepConfigLmSlmTestId OBJECT-TYPE
    SYNTAX      Unsigned32
    MAX-ACCESS  read-write
    STATUS      current
    DESCRIPTION
        "Test ID value to use in SLM PDUs."
    ::= { gamMepConfigLmEntry 19 }

gamMepConfigDm OBJECT IDENTIFIER
    ::= { gamMepConfig 5 }

gamMepConfigDmTable OBJECT-TYPE
    SYNTAX      SEQUENCE OF GAMMepConfigDmEntry
    MAX-ACCESS  not-accessible
    STATUS      current
    DESCRIPTION
        "This is a table of created instance Delay Measurement configuration
         parameters"
    ::= { gamMepConfigDm 1 }

gamMepConfigDmEntry OBJECT-TYPE
    SYNTAX      GAMMepConfigDmEntry
    MAX-ACCESS  not-accessible
    STATUS      current
    DESCRIPTION
        "This is a created instance Delay Measurement parameters."
    INDEX       { gamMepConfigDmId }
    ::= { gamMepConfigDmTable 1 }

GAMMepConfigDmEntry ::= SEQUENCE {
    gamMepConfigDmId            Integer32,
    gamMepConfigDmEnable        TruthValue,
    gamMepConfigDmEnded         GAMMepEnded,
    gamMepConfigDmPrio          Unsigned32,
    gamMepConfigDmCast          GAMMepCast,
    gamMepConfigDmMep           Unsigned32,
    gamMepConfigDmCalcWay       GAMMepDmCalcWay,
    gamMepConfigDmInterval      Unsigned32,
    gamMepConfigDmLastN         Unsigned32,
    gamMepConfigDmTimeUnit      GAMMepDmTimeUnit,
    gamMepConfigDmOverflowAct   GAMMepDmOverflowAction,
    gamMepConfigDmSynchronized  TruthValue,
    gamMepConfigDmNumOfBinFD    GAMUnsigned16,
    gamMepConfigDmNumOfBinIFDV  GAMUnsigned16,
    gamMepConfigDmMThreshold    Unsigned32
}

gamMepConfigDmId OBJECT-TYPE
    SYNTAX      Integer32 (1..2147483647)
    MAX-ACCESS  accessible-for-notify
    STATUS      current
    DESCRIPTION
        "The MEP instance ID"
    ::= { gamMepConfigDmEntry 1 }

gamMepConfigDmEnable OBJECT-TYPE
    SYNTAX      TruthValue
    MAX-ACCESS  read-write
    STATUS      current
    DESCRIPTION
        "Delay Measurement is enabled"
    ::= { gamMepConfigDmEntry 2 }

gamMepConfigDmEnded OBJECT-TYPE
    SYNTAX      GAMMepEnded
    MAX-ACCESS  read-write
    STATUS      current
    DESCRIPTION
        "Dual/single ended selection. CCM or LMM/LMR based. Cannot be changed
         after creation."
    ::= { gamMepConfigDmEntry 3 }

gamMepConfigDmPrio OBJECT-TYPE
    SYNTAX      Unsigned32
    MAX-ACCESS  read-write
    STATUS      current
    DESCRIPTION
        "Priority of the transmitted DM PDU. Range 0 to 7"
    ::= { gamMepConfigDmEntry 5 }

gamMepConfigDmCast OBJECT-TYPE
    SYNTAX      GAMMepCast
    MAX-ACCESS  read-write
    STATUS      current
    DESCRIPTION
        "Uni/Multicast selection"
    ::= { gamMepConfigDmEntry 6 }

gamMepConfigDmMep OBJECT-TYPE
    SYNTAX      Unsigned32
    MAX-ACCESS  read-write
    STATUS      current
    DESCRIPTION
        "Peer MEP to receive DMM/1DM - only used if unicast"
    ::= { gamMepConfigDmEntry 7 }

gamMepConfigDmCalcWay OBJECT-TYPE
    SYNTAX      GAMMepDmCalcWay
    MAX-ACCESS  read-write
    STATUS      current
    DESCRIPTION
        "Round trip or flow calculation way selection."
    ::= { gamMepConfigDmEntry 8 }

gamMepConfigDmInterval OBJECT-TYPE
    SYNTAX      Unsigned32
    MAX-ACCESS  read-write
    STATUS      current
    DESCRIPTION
        "Interval between 1DM/DMM in 10 ms. Range Capability dm_interval_min to
         dm_interval_max."
    ::= { gamMepConfigDmEntry 9 }

gamMepConfigDmLastN OBJECT-TYPE
    SYNTAX      Unsigned32
    MAX-ACCESS  read-write
    STATUS      current
    DESCRIPTION
        "The number of last N measurements used to calculate average delay and
         variation. Range Capability dm_lastn_min to dm_lastn_max."
    ::= { gamMepConfigDmEntry 10 }

gamMepConfigDmTimeUnit OBJECT-TYPE
    SYNTAX      GAMMepDmTimeUnit
    MAX-ACCESS  read-write
    STATUS      current
    DESCRIPTION
        "Calculation time unit."
    ::= { gamMepConfigDmEntry 11 }

gamMepConfigDmOverflowAct OBJECT-TYPE
    SYNTAX      GAMMepDmOverflowAction
    MAX-ACCESS  read-write
    STATUS      current
    DESCRIPTION
        "Action when internal total delay counter overflow."
    ::= { gamMepConfigDmEntry 12 }

gamMepConfigDmSynchronized OBJECT-TYPE
    SYNTAX      TruthValue
    MAX-ACCESS  read-write
    STATUS      current
    DESCRIPTION
        "Near-end and far-end is real-time synchronized. One-way DM calculation
         on receiving DMR."
    ::= { gamMepConfigDmEntry 13 }

gamMepConfigDmNumOfBinFD OBJECT-TYPE
    SYNTAX      GAMUnsigned16
    MAX-ACCESS  read-write
    STATUS      current
    DESCRIPTION
        "Configurable number of FD Measurement Bins / per Measurement Interval.
         default:3, min:2, max:10"
    ::= { gamMepConfigDmEntry 14 }

gamMepConfigDmNumOfBinIFDV OBJECT-TYPE
    SYNTAX      GAMUnsigned16
    MAX-ACCESS  read-write
    STATUS      current
    DESCRIPTION
        "Configurable number of IFDV Measurement Bins / per Measurement
         Interval. default:2, min:2, max:10"
    ::= { gamMepConfigDmEntry 15 }

gamMepConfigDmMThreshold OBJECT-TYPE
    SYNTAX      Unsigned32
    MAX-ACCESS  read-write
    STATUS      current
    DESCRIPTION
        "Configurable the measurement threshold for each Measurement Bin.
         default: 5000"
    ::= { gamMepConfigDmEntry 16 }

gamMepConfigLb OBJECT IDENTIFIER
    ::= { gamMepConfig 6 }

gamMepConfigLbTable OBJECT-TYPE
    SYNTAX      SEQUENCE OF GAMMepConfigLbEntry
    MAX-ACCESS  not-accessible
    STATUS      current
    DESCRIPTION
        "This is a table of created instance Loop Back configuration parameters"
    ::= { gamMepConfigLb 1 }

gamMepConfigLbEntry OBJECT-TYPE
    SYNTAX      GAMMepConfigLbEntry
    MAX-ACCESS  not-accessible
    STATUS      current
    DESCRIPTION
        "This is a created instance Loop Back parameters. This cannot be changed"
    INDEX       { gamMepConfigLbId }
    ::= { gamMepConfigLbTable 1 }

GAMMepConfigLbEntry ::= SEQUENCE {
    gamMepConfigLbId          Integer32,
    gamMepConfigLbDei         TruthValue,
    gamMepConfigLbPrio        Unsigned32,
    gamMepConfigLbCast        GAMMepCast,
    gamMepConfigLbMep         Unsigned32,
    gamMepConfigLbMac         MacAddress,
    gamMepConfigLbToSend      Unsigned32,
    gamMepConfigLbSize        Unsigned32,
    gamMepConfigLbInterval    Unsigned32,
    gamMepConfigLbTimeToLive  GAMUnsigned8,
    gamMepConfigLbAction      GAMRowEditorState
}

gamMepConfigLbId OBJECT-TYPE
    SYNTAX      Integer32 (1..2147483647)
    MAX-ACCESS  accessible-for-notify
    STATUS      current
    DESCRIPTION
        "The MEP instance ID"
    ::= { gamMepConfigLbEntry 1 }

gamMepConfigLbDei OBJECT-TYPE
    SYNTAX      TruthValue
    MAX-ACCESS  read-write
    STATUS      current
    DESCRIPTION
        "Drop Eligibility Indicator of transmitted LBM PDU"
    ::= { gamMepConfigLbEntry 2 }

gamMepConfigLbPrio OBJECT-TYPE
    SYNTAX      Unsigned32
    MAX-ACCESS  read-write
    STATUS      current
    DESCRIPTION
        "Priority of the transmitted LBM PDU. Range 0 to 7"
    ::= { gamMepConfigLbEntry 3 }

gamMepConfigLbCast OBJECT-TYPE
    SYNTAX      GAMMepCast
    MAX-ACCESS  read-write
    STATUS      current
    DESCRIPTION
        "Uni/Multicast selection"
    ::= { gamMepConfigLbEntry 4 }

gamMepConfigLbMep OBJECT-TYPE
    SYNTAX      Unsigned32
    MAX-ACCESS  read-write
    STATUS      current
    DESCRIPTION
        "Peer MEP to receive LBM - only used if unicast and 'mac' is 'all zero'."
    ::= { gamMepConfigLbEntry 5 }

gamMepConfigLbMac OBJECT-TYPE
    SYNTAX      MacAddress
    MAX-ACCESS  read-write
    STATUS      current
    DESCRIPTION
        "Unicast MAC address to receive LBM - has to be used to send LBM to MIP."
    ::= { gamMepConfigLbEntry 6 }

gamMepConfigLbToSend OBJECT-TYPE
    SYNTAX      Unsigned32
    MAX-ACCESS  read-write
    STATUS      current
    DESCRIPTION
        "Number of LBM to send. Capability lb_to_send_infinite => test
         behaviour. Requires VOE."
    ::= { gamMepConfigLbEntry 7 }

gamMepConfigLbSize OBJECT-TYPE
    SYNTAX      Unsigned32
    MAX-ACCESS  read-write
    STATUS      current
    DESCRIPTION
        "Size of LBM frame to send - Range Capability lbm_size_min to
         lbm_size_max"
    ::= { gamMepConfigLbEntry 8 }

gamMepConfigLbInterval OBJECT-TYPE
    SYNTAX      Unsigned32
    MAX-ACCESS  read-write
    STATUS      current
    DESCRIPTION
        "Frame interval.
         
         If 'ToSend' != Capability lb_to_send_infinite then the 'Interval' is in
         10 ms. Max 1 s.
         
         If 'ToSend' == Capability lb_to_send_infinite then the 'Interval' is in
         1 us. Max 10 ms."
    ::= { gamMepConfigLbEntry 9 }

gamMepConfigLbTimeToLive OBJECT-TYPE
    SYNTAX      GAMUnsigned8
    MAX-ACCESS  read-write
    STATUS      current
    DESCRIPTION
        "Time To Live."
    ::= { gamMepConfigLbEntry 10 }

gamMepConfigLbAction OBJECT-TYPE
    SYNTAX      GAMRowEditorState
    MAX-ACCESS  read-write
    STATUS      current
    DESCRIPTION
        "Action"
    ::= { gamMepConfigLbEntry 101 }

gamMepConfigLbRowEditor OBJECT IDENTIFIER
    ::= { gamMepConfigLb 2 }

gamMepConfigLbRowEditorId OBJECT-TYPE
    SYNTAX      Integer32 (1..2147483647)
    MAX-ACCESS  read-write
    STATUS      current
    DESCRIPTION
        "The MEP instance ID"
    ::= { gamMepConfigLbRowEditor 1 }

gamMepConfigLbRowEditorDei OBJECT-TYPE
    SYNTAX      TruthValue
    MAX-ACCESS  read-write
    STATUS      current
    DESCRIPTION
        "Drop Eligibility Indicator of transmitted LBM PDU"
    ::= { gamMepConfigLbRowEditor 2 }

gamMepConfigLbRowEditorPrio OBJECT-TYPE
    SYNTAX      Unsigned32
    MAX-ACCESS  read-write
    STATUS      current
    DESCRIPTION
        "Priority of the transmitted LBM PDU. Range 0 to 7"
    ::= { gamMepConfigLbRowEditor 3 }

gamMepConfigLbRowEditorCast OBJECT-TYPE
    SYNTAX      GAMMepCast
    MAX-ACCESS  read-write
    STATUS      current
    DESCRIPTION
        "Uni/Multicast selection"
    ::= { gamMepConfigLbRowEditor 4 }

gamMepConfigLbRowEditorMep OBJECT-TYPE
    SYNTAX      Unsigned32
    MAX-ACCESS  read-write
    STATUS      current
    DESCRIPTION
        "Peer MEP to receive LBM - only used if unicast and 'mac' is 'all zero'."
    ::= { gamMepConfigLbRowEditor 5 }

gamMepConfigLbRowEditorMac OBJECT-TYPE
    SYNTAX      MacAddress
    MAX-ACCESS  read-write
    STATUS      current
    DESCRIPTION
        "Unicast MAC address to receive LBM - has to be used to send LBM to MIP."
    ::= { gamMepConfigLbRowEditor 6 }

gamMepConfigLbRowEditorToSend OBJECT-TYPE
    SYNTAX      Unsigned32
    MAX-ACCESS  read-write
    STATUS      current
    DESCRIPTION
        "Number of LBM to send. Capability lb_to_send_infinite => test
         behaviour. Requires VOE."
    ::= { gamMepConfigLbRowEditor 7 }

gamMepConfigLbRowEditorSize OBJECT-TYPE
    SYNTAX      Unsigned32
    MAX-ACCESS  read-write
    STATUS      current
    DESCRIPTION
        "Size of LBM frame to send - Range Capability lbm_size_min to
         lbm_size_max"
    ::= { gamMepConfigLbRowEditor 8 }

gamMepConfigLbRowEditorInterval OBJECT-TYPE
    SYNTAX      Unsigned32
    MAX-ACCESS  read-write
    STATUS      current
    DESCRIPTION
        "Frame interval.
         
         If 'ToSend' != Capability lb_to_send_infinite then the 'Interval' is in
         10 ms. Max 1 s.
         
         If 'ToSend' == Capability lb_to_send_infinite then the 'Interval' is in
         1 us. Max 10 ms."
    ::= { gamMepConfigLbRowEditor 9 }

gamMepConfigLbRowEditorTimeToLive OBJECT-TYPE
    SYNTAX      GAMUnsigned8
    MAX-ACCESS  read-write
    STATUS      current
    DESCRIPTION
        "Time To Live."
    ::= { gamMepConfigLbRowEditor 10 }

gamMepConfigLbRowEditorAction OBJECT-TYPE
    SYNTAX      GAMRowEditorState
    MAX-ACCESS  read-write
    STATUS      current
    DESCRIPTION
        "Action"
    ::= { gamMepConfigLbRowEditor 101 }

gamMepConfigTst OBJECT IDENTIFIER
    ::= { gamMepConfig 7 }

gamMepConfigTstTable OBJECT-TYPE
    SYNTAX      SEQUENCE OF GAMMepConfigTstEntry
    MAX-ACCESS  not-accessible
    STATUS      current
    DESCRIPTION
        "This is a table of created instance Test Signal configuration
         parameters"
    ::= { gamMepConfigTst 1 }

gamMepConfigTstEntry OBJECT-TYPE
    SYNTAX      GAMMepConfigTstEntry
    MAX-ACCESS  not-accessible
    STATUS      current
    DESCRIPTION
        "This is a created instance Test Signal parameters."
    INDEX       { gamMepConfigTstId }
    ::= { gamMepConfigTstTable 1 }

GAMMepConfigTstEntry ::= SEQUENCE {
    gamMepConfigTstId        Integer32,
    gamMepConfigTstTxEnable  TruthValue,
    gamMepConfigTstRxEnable  TruthValue,
    gamMepConfigTstDei       TruthValue,
    gamMepConfigTstPrio      Unsigned32,
    gamMepConfigTstMep       Unsigned32,
    gamMepConfigTstRate      Unsigned32,
    gamMepConfigTstSize      Unsigned32,
    gamMepConfigTstPattern   GAMMepTstPattern,
    gamMepConfigTstSequence  TruthValue,
    gamMepConfigTstAction    GAMRowEditorState
}

gamMepConfigTstId OBJECT-TYPE
    SYNTAX      Integer32 (1..2147483647)
    MAX-ACCESS  accessible-for-notify
    STATUS      current
    DESCRIPTION
        "The MEP instance ID"
    ::= { gamMepConfigTstEntry 1 }

gamMepConfigTstTxEnable OBJECT-TYPE
    SYNTAX      TruthValue
    MAX-ACCESS  read-write
    STATUS      current
    DESCRIPTION
        "Enable/disable transmission of TST PDU."
    ::= { gamMepConfigTstEntry 2 }

gamMepConfigTstRxEnable OBJECT-TYPE
    SYNTAX      TruthValue
    MAX-ACCESS  read-write
    STATUS      current
    DESCRIPTION
        "Enable/disable reception and analyse of TST PDU."
    ::= { gamMepConfigTstEntry 3 }

gamMepConfigTstDei OBJECT-TYPE
    SYNTAX      TruthValue
    MAX-ACCESS  read-write
    STATUS      current
    DESCRIPTION
        "Drop Eligibility Indicator of transmitted TST PDU"
    ::= { gamMepConfigTstEntry 4 }

gamMepConfigTstPrio OBJECT-TYPE
    SYNTAX      Unsigned32
    MAX-ACCESS  read-write
    STATUS      current
    DESCRIPTION
        "Priority of the transmitted TST PDU. Range 0 to 7"
    ::= { gamMepConfigTstEntry 5 }

gamMepConfigTstMep OBJECT-TYPE
    SYNTAX      Unsigned32
    MAX-ACCESS  read-write
    STATUS      current
    DESCRIPTION
        "Peer MEP to receive TST"
    ::= { gamMepConfigTstEntry 6 }

gamMepConfigTstRate OBJECT-TYPE
    SYNTAX      Unsigned32
    MAX-ACCESS  read-write
    STATUS      current
    DESCRIPTION
        "The transmission rate in Kbps - Range 1 to Capability tst_rate_max."
    ::= { gamMepConfigTstEntry 7 }

gamMepConfigTstSize OBJECT-TYPE
    SYNTAX      Unsigned32
    MAX-ACCESS  read-write
    STATUS      current
    DESCRIPTION
        "Size of TST frame to send - Range Capability tst_size_min to
         tst_size_max."
    ::= { gamMepConfigTstEntry 8 }

gamMepConfigTstPattern OBJECT-TYPE
    SYNTAX      GAMMepTstPattern
    MAX-ACCESS  read-write
    STATUS      current
    DESCRIPTION
        "Pattern in TST frame Data TLV."
    ::= { gamMepConfigTstEntry 9 }

gamMepConfigTstSequence OBJECT-TYPE
    SYNTAX      TruthValue
    MAX-ACCESS  read-write
    STATUS      current
    DESCRIPTION
        "Sequence number will be inserted - not checked in receiver on Caracal
         and Jaguar."
    ::= { gamMepConfigTstEntry 10 }

gamMepConfigTstAction OBJECT-TYPE
    SYNTAX      GAMRowEditorState
    MAX-ACCESS  read-write
    STATUS      current
    DESCRIPTION
        "Action"
    ::= { gamMepConfigTstEntry 101 }

gamMepConfigTstRowEditor OBJECT IDENTIFIER
    ::= { gamMepConfigTst 2 }

gamMepConfigTstRowEditorId OBJECT-TYPE
    SYNTAX      Integer32 (1..2147483647)
    MAX-ACCESS  read-write
    STATUS      current
    DESCRIPTION
        "The MEP instance ID"
    ::= { gamMepConfigTstRowEditor 1 }

gamMepConfigTstRowEditorTxEnable OBJECT-TYPE
    SYNTAX      TruthValue
    MAX-ACCESS  read-write
    STATUS      current
    DESCRIPTION
        "Enable/disable transmission of TST PDU."
    ::= { gamMepConfigTstRowEditor 2 }

gamMepConfigTstRowEditorRxEnable OBJECT-TYPE
    SYNTAX      TruthValue
    MAX-ACCESS  read-write
    STATUS      current
    DESCRIPTION
        "Enable/disable reception and analyse of TST PDU."
    ::= { gamMepConfigTstRowEditor 3 }

gamMepConfigTstRowEditorDei OBJECT-TYPE
    SYNTAX      TruthValue
    MAX-ACCESS  read-write
    STATUS      current
    DESCRIPTION
        "Drop Eligibility Indicator of transmitted TST PDU"
    ::= { gamMepConfigTstRowEditor 4 }

gamMepConfigTstRowEditorPrio OBJECT-TYPE
    SYNTAX      Unsigned32
    MAX-ACCESS  read-write
    STATUS      current
    DESCRIPTION
        "Priority of the transmitted TST PDU. Range 0 to 7"
    ::= { gamMepConfigTstRowEditor 5 }

gamMepConfigTstRowEditorMep OBJECT-TYPE
    SYNTAX      Unsigned32
    MAX-ACCESS  read-write
    STATUS      current
    DESCRIPTION
        "Peer MEP to receive TST"
    ::= { gamMepConfigTstRowEditor 6 }

gamMepConfigTstRowEditorRate OBJECT-TYPE
    SYNTAX      Unsigned32
    MAX-ACCESS  read-write
    STATUS      current
    DESCRIPTION
        "The transmission rate in Kbps - Range 1 to Capability tst_rate_max."
    ::= { gamMepConfigTstRowEditor 7 }

gamMepConfigTstRowEditorSize OBJECT-TYPE
    SYNTAX      Unsigned32
    MAX-ACCESS  read-write
    STATUS      current
    DESCRIPTION
        "Size of TST frame to send - Range Capability tst_size_min to
         tst_size_max."
    ::= { gamMepConfigTstRowEditor 8 }

gamMepConfigTstRowEditorPattern OBJECT-TYPE
    SYNTAX      GAMMepTstPattern
    MAX-ACCESS  read-write
    STATUS      current
    DESCRIPTION
        "Pattern in TST frame Data TLV."
    ::= { gamMepConfigTstRowEditor 9 }

gamMepConfigTstRowEditorSequence OBJECT-TYPE
    SYNTAX      TruthValue
    MAX-ACCESS  read-write
    STATUS      current
    DESCRIPTION
        "Sequence number will be inserted - not checked in receiver on Caracal
         and Jaguar."
    ::= { gamMepConfigTstRowEditor 10 }

gamMepConfigTstRowEditorAction OBJECT-TYPE
    SYNTAX      GAMRowEditorState
    MAX-ACCESS  read-write
    STATUS      current
    DESCRIPTION
        "Action"
    ::= { gamMepConfigTstRowEditor 101 }

gamMepConfigLt OBJECT IDENTIFIER
    ::= { gamMepConfig 8 }

gamMepConfigLtTable OBJECT-TYPE
    SYNTAX      SEQUENCE OF GAMMepConfigLtEntry
    MAX-ACCESS  not-accessible
    STATUS      current
    DESCRIPTION
        "This is a table of created instance Link Trace configuration parameters"
    ::= { gamMepConfigLt 1 }

gamMepConfigLtEntry OBJECT-TYPE
    SYNTAX      GAMMepConfigLtEntry
    MAX-ACCESS  not-accessible
    STATUS      current
    DESCRIPTION
        "This is a created instance Link Trace parameters. This cannot be
         changed"
    INDEX       { gamMepConfigLtId }
    ::= { gamMepConfigLtTable 1 }

GAMMepConfigLtEntry ::= SEQUENCE {
    gamMepConfigLtId          Integer32,
    gamMepConfigLtPrio        Unsigned32,
    gamMepConfigLtMep         Unsigned32,
    gamMepConfigLtMac         MacAddress,
    gamMepConfigLtTimeToLive  Unsigned32,
    gamMepConfigLtAction      GAMRowEditorState
}

gamMepConfigLtId OBJECT-TYPE
    SYNTAX      Integer32 (1..2147483647)
    MAX-ACCESS  accessible-for-notify
    STATUS      current
    DESCRIPTION
        "The MEP instance ID"
    ::= { gamMepConfigLtEntry 1 }

gamMepConfigLtPrio OBJECT-TYPE
    SYNTAX      Unsigned32
    MAX-ACCESS  read-write
    STATUS      current
    DESCRIPTION
        "Priority of the transmitted LTM PDU. Range 0 to 7"
    ::= { gamMepConfigLtEntry 3 }

gamMepConfigLtMep OBJECT-TYPE
    SYNTAX      Unsigned32
    MAX-ACCESS  read-write
    STATUS      current
    DESCRIPTION
        "Target Peer Mep to receive LTM - only used if 'mac' is 'all zero'"
    ::= { gamMepConfigLtEntry 4 }

gamMepConfigLtMac OBJECT-TYPE
    SYNTAX      MacAddress
    MAX-ACCESS  read-write
    STATUS      current
    DESCRIPTION
        "Unicast MAC address to receive LTM - has to be used to send LTM to MIP."
    ::= { gamMepConfigLtEntry 5 }

gamMepConfigLtTimeToLive OBJECT-TYPE
    SYNTAX      Unsigned32
    MAX-ACCESS  read-write
    STATUS      current
    DESCRIPTION
        "Time To Live."
    ::= { gamMepConfigLtEntry 6 }

gamMepConfigLtAction OBJECT-TYPE
    SYNTAX      GAMRowEditorState
    MAX-ACCESS  read-write
    STATUS      current
    DESCRIPTION
        "Action"
    ::= { gamMepConfigLtEntry 101 }

gamMepConfigLtRowEditor OBJECT IDENTIFIER
    ::= { gamMepConfigLt 2 }

gamMepConfigLtRowEditorId OBJECT-TYPE
    SYNTAX      Integer32 (1..2147483647)
    MAX-ACCESS  read-write
    STATUS      current
    DESCRIPTION
        "The MEP instance ID"
    ::= { gamMepConfigLtRowEditor 1 }

gamMepConfigLtRowEditorPrio OBJECT-TYPE
    SYNTAX      Unsigned32
    MAX-ACCESS  read-write
    STATUS      current
    DESCRIPTION
        "Priority of the transmitted LTM PDU. Range 0 to 7"
    ::= { gamMepConfigLtRowEditor 3 }

gamMepConfigLtRowEditorMep OBJECT-TYPE
    SYNTAX      Unsigned32
    MAX-ACCESS  read-write
    STATUS      current
    DESCRIPTION
        "Target Peer Mep to receive LTM - only used if 'mac' is 'all zero'"
    ::= { gamMepConfigLtRowEditor 4 }

gamMepConfigLtRowEditorMac OBJECT-TYPE
    SYNTAX      MacAddress
    MAX-ACCESS  read-write
    STATUS      current
    DESCRIPTION
        "Unicast MAC address to receive LTM - has to be used to send LTM to MIP."
    ::= { gamMepConfigLtRowEditor 5 }

gamMepConfigLtRowEditorTimeToLive OBJECT-TYPE
    SYNTAX      Unsigned32
    MAX-ACCESS  read-write
    STATUS      current
    DESCRIPTION
        "Time To Live."
    ::= { gamMepConfigLtRowEditor 6 }

gamMepConfigLtRowEditorAction OBJECT-TYPE
    SYNTAX      GAMRowEditorState
    MAX-ACCESS  read-write
    STATUS      current
    DESCRIPTION
        "Action"
    ::= { gamMepConfigLtRowEditor 101 }

gamMepConfigAps OBJECT IDENTIFIER
    ::= { gamMepConfig 9 }

gamMepConfigApsTable OBJECT-TYPE
    SYNTAX      SEQUENCE OF GAMMepConfigApsEntry
    MAX-ACCESS  not-accessible
    STATUS      current
    DESCRIPTION
        "This is a table of created instance Automatic Protection Switching
         configuration parameters"
    ::= { gamMepConfigAps 1 }

gamMepConfigApsEntry OBJECT-TYPE
    SYNTAX      GAMMepConfigApsEntry
    MAX-ACCESS  not-accessible
    STATUS      current
    DESCRIPTION
        "This is a created instance Automatic Protection Switching parameters."
    INDEX       { gamMepConfigApsId }
    ::= { gamMepConfigApsTable 1 }

GAMMepConfigApsEntry ::= SEQUENCE {
    gamMepConfigApsId         Integer32,
    gamMepConfigApsPrio       Unsigned32,
    gamMepConfigApsApsType    GAMMepApsType,
    gamMepConfigApsCast       GAMMepCast,
    gamMepConfigApsRapsOctet  Unsigned32,
    gamMepConfigApsAction     GAMRowEditorState
}

gamMepConfigApsId OBJECT-TYPE
    SYNTAX      Integer32 (1..2147483647)
    MAX-ACCESS  accessible-for-notify
    STATUS      current
    DESCRIPTION
        "The MEP instance ID"
    ::= { gamMepConfigApsEntry 1 }

gamMepConfigApsPrio OBJECT-TYPE
    SYNTAX      Unsigned32
    MAX-ACCESS  read-write
    STATUS      current
    DESCRIPTION
        "Priority of the transmitted APS PDU. Range 0 to 7"
    ::= { gamMepConfigApsEntry 3 }

gamMepConfigApsApsType OBJECT-TYPE
    SYNTAX      GAMMepApsType
    MAX-ACCESS  read-write
    STATUS      current
    DESCRIPTION
        "Type of APS"
    ::= { gamMepConfigApsEntry 4 }

gamMepConfigApsCast OBJECT-TYPE
    SYNTAX      GAMMepCast
    MAX-ACCESS  read-write
    STATUS      current
    DESCRIPTION
        "Uni/multicast selection"
    ::= { gamMepConfigApsEntry 5 }

gamMepConfigApsRapsOctet OBJECT-TYPE
    SYNTAX      Unsigned32
    MAX-ACCESS  read-write
    STATUS      current
    DESCRIPTION
        "Last octet in the R-APS multicast DA"
    ::= { gamMepConfigApsEntry 6 }

gamMepConfigApsAction OBJECT-TYPE
    SYNTAX      GAMRowEditorState
    MAX-ACCESS  read-write
    STATUS      current
    DESCRIPTION
        "Action"
    ::= { gamMepConfigApsEntry 101 }

gamMepConfigApsRowEditor OBJECT IDENTIFIER
    ::= { gamMepConfigAps 2 }

gamMepConfigApsRowEditorId OBJECT-TYPE
    SYNTAX      Integer32 (1..2147483647)
    MAX-ACCESS  read-write
    STATUS      current
    DESCRIPTION
        "The MEP instance ID"
    ::= { gamMepConfigApsRowEditor 1 }

gamMepConfigApsRowEditorPrio OBJECT-TYPE
    SYNTAX      Unsigned32
    MAX-ACCESS  read-write
    STATUS      current
    DESCRIPTION
        "Priority of the transmitted APS PDU. Range 0 to 7"
    ::= { gamMepConfigApsRowEditor 3 }

gamMepConfigApsRowEditorApsType OBJECT-TYPE
    SYNTAX      GAMMepApsType
    MAX-ACCESS  read-write
    STATUS      current
    DESCRIPTION
        "Type of APS"
    ::= { gamMepConfigApsRowEditor 4 }

gamMepConfigApsRowEditorCast OBJECT-TYPE
    SYNTAX      GAMMepCast
    MAX-ACCESS  read-write
    STATUS      current
    DESCRIPTION
        "Uni/multicast selection"
    ::= { gamMepConfigApsRowEditor 5 }

gamMepConfigApsRowEditorRapsOctet OBJECT-TYPE
    SYNTAX      Unsigned32
    MAX-ACCESS  read-write
    STATUS      current
    DESCRIPTION
        "Last octet in the R-APS multicast DA"
    ::= { gamMepConfigApsRowEditor 6 }

gamMepConfigApsRowEditorAction OBJECT-TYPE
    SYNTAX      GAMRowEditorState
    MAX-ACCESS  read-write
    STATUS      current
    DESCRIPTION
        "Action"
    ::= { gamMepConfigApsRowEditor 101 }

gamMepConfigAis OBJECT IDENTIFIER
    ::= { gamMepConfig 10 }

gamMepConfigAisTable OBJECT-TYPE
    SYNTAX      SEQUENCE OF GAMMepConfigAisEntry
    MAX-ACCESS  not-accessible
    STATUS      current
    DESCRIPTION
        "This is a table of created instance Alarm Indication Signal
         configuration parameters"
    ::= { gamMepConfigAis 1 }

gamMepConfigAisEntry OBJECT-TYPE
    SYNTAX      GAMMepConfigAisEntry
    MAX-ACCESS  not-accessible
    STATUS      current
    DESCRIPTION
        "This is a created instance Alarm Indication Signal parameters."
    INDEX       { gamMepConfigAisId }
    ::= { gamMepConfigAisTable 1 }

GAMMepConfigAisEntry ::= SEQUENCE {
    gamMepConfigAisId          Integer32,
    gamMepConfigAisProtection  TruthValue,
    gamMepConfigAisRate        GAMMepTxRate,
    gamMepConfigAisAction      GAMRowEditorState
}

gamMepConfigAisId OBJECT-TYPE
    SYNTAX      Integer32 (1..2147483647)
    MAX-ACCESS  accessible-for-notify
    STATUS      current
    DESCRIPTION
        "The MEP instance ID"
    ::= { gamMepConfigAisEntry 1 }

gamMepConfigAisProtection OBJECT-TYPE
    SYNTAX      TruthValue
    MAX-ACCESS  read-write
    STATUS      current
    DESCRIPTION
        "The first three AIS frames are transmitted as fast as possible."
    ::= { gamMepConfigAisEntry 2 }

gamMepConfigAisRate OBJECT-TYPE
    SYNTAX      GAMMepTxRate
    MAX-ACCESS  read-write
    STATUS      current
    DESCRIPTION
        "AIS transmission rate"
    ::= { gamMepConfigAisEntry 3 }

gamMepConfigAisAction OBJECT-TYPE
    SYNTAX      GAMRowEditorState
    MAX-ACCESS  read-write
    STATUS      current
    DESCRIPTION
        "Action"
    ::= { gamMepConfigAisEntry 101 }

gamMepConfigAisRowEditor OBJECT IDENTIFIER
    ::= { gamMepConfigAis 2 }

gamMepConfigAisRowEditorId OBJECT-TYPE
    SYNTAX      Integer32 (1..2147483647)
    MAX-ACCESS  read-write
    STATUS      current
    DESCRIPTION
        "The MEP instance ID"
    ::= { gamMepConfigAisRowEditor 1 }

gamMepConfigAisRowEditorProtection OBJECT-TYPE
    SYNTAX      TruthValue
    MAX-ACCESS  read-write
    STATUS      current
    DESCRIPTION
        "The first three AIS frames are transmitted as fast as possible."
    ::= { gamMepConfigAisRowEditor 2 }

gamMepConfigAisRowEditorRate OBJECT-TYPE
    SYNTAX      GAMMepTxRate
    MAX-ACCESS  read-write
    STATUS      current
    DESCRIPTION
        "AIS transmission rate"
    ::= { gamMepConfigAisRowEditor 3 }

gamMepConfigAisRowEditorAction OBJECT-TYPE
    SYNTAX      GAMRowEditorState
    MAX-ACCESS  read-write
    STATUS      current
    DESCRIPTION
        "Action"
    ::= { gamMepConfigAisRowEditor 101 }

gamMepConfigLck OBJECT IDENTIFIER
    ::= { gamMepConfig 11 }

gamMepConfigLckTable OBJECT-TYPE
    SYNTAX      SEQUENCE OF GAMMepConfigLckEntry
    MAX-ACCESS  not-accessible
    STATUS      current
    DESCRIPTION
        "This is a table of created instance Locked Signal configuration
         parameters"
    ::= { gamMepConfigLck 1 }

gamMepConfigLckEntry OBJECT-TYPE
    SYNTAX      GAMMepConfigLckEntry
    MAX-ACCESS  not-accessible
    STATUS      current
    DESCRIPTION
        "This is a created instance Locked Signal parameters."
    INDEX       { gamMepConfigLckId }
    ::= { gamMepConfigLckTable 1 }

GAMMepConfigLckEntry ::= SEQUENCE {
    gamMepConfigLckId      Integer32,
    gamMepConfigLckRate    GAMMepTxRate,
    gamMepConfigLckAction  GAMRowEditorState
}

gamMepConfigLckId OBJECT-TYPE
    SYNTAX      Integer32 (1..2147483647)
    MAX-ACCESS  accessible-for-notify
    STATUS      current
    DESCRIPTION
        "The MEP instance ID"
    ::= { gamMepConfigLckEntry 1 }

gamMepConfigLckRate OBJECT-TYPE
    SYNTAX      GAMMepTxRate
    MAX-ACCESS  read-write
    STATUS      current
    DESCRIPTION
        "LCK transmission rate"
    ::= { gamMepConfigLckEntry 2 }

gamMepConfigLckAction OBJECT-TYPE
    SYNTAX      GAMRowEditorState
    MAX-ACCESS  read-write
    STATUS      current
    DESCRIPTION
        "Action"
    ::= { gamMepConfigLckEntry 101 }

gamMepConfigLckRowEditor OBJECT IDENTIFIER
    ::= { gamMepConfigLck 2 }

gamMepConfigLckRowEditorId OBJECT-TYPE
    SYNTAX      Integer32 (1..2147483647)
    MAX-ACCESS  read-write
    STATUS      current
    DESCRIPTION
        "The MEP instance ID"
    ::= { gamMepConfigLckRowEditor 1 }

gamMepConfigLckRowEditorRate OBJECT-TYPE
    SYNTAX      GAMMepTxRate
    MAX-ACCESS  read-write
    STATUS      current
    DESCRIPTION
        "LCK transmission rate"
    ::= { gamMepConfigLckRowEditor 2 }

gamMepConfigLckRowEditorAction OBJECT-TYPE
    SYNTAX      GAMRowEditorState
    MAX-ACCESS  read-write
    STATUS      current
    DESCRIPTION
        "Action"
    ::= { gamMepConfigLckRowEditor 101 }

gamMepConfigClient OBJECT IDENTIFIER
    ::= { gamMepConfig 12 }

gamMepConfigClientFlowTable OBJECT-TYPE
    SYNTAX      SEQUENCE OF GAMMepConfigClientFlowEntry
    MAX-ACCESS  not-accessible
    STATUS      current
    DESCRIPTION
        "This is a table of client flow configuration parameters"
    ::= { gamMepConfigClient 2 }

gamMepConfigClientFlowEntry OBJECT-TYPE
    SYNTAX      GAMMepConfigClientFlowEntry
    MAX-ACCESS  not-accessible
    STATUS      current
    DESCRIPTION
        "This is a client flow configuration parameters"
    INDEX       { gamMepConfigClientFlowId,
                  gamMepConfigClientFlowFlowId }
    ::= { gamMepConfigClientFlowTable 1 }

GAMMepConfigClientFlowEntry ::= SEQUENCE {
    gamMepConfigClientFlowId       Integer32,
    gamMepConfigClientFlowFlowId   GAMInterfaceIndex,
    gamMepConfigClientFlowAisPrio  GAMUnsigned8,
    gamMepConfigClientFlowLckPrio  GAMUnsigned8,
    gamMepConfigClientFlowLevel    GAMUnsigned8,
    gamMepConfigClientFlowAction   GAMRowEditorState
}

gamMepConfigClientFlowId OBJECT-TYPE
    SYNTAX      Integer32 (1..2147483647)
    MAX-ACCESS  accessible-for-notify
    STATUS      current
    DESCRIPTION
        "The MEP instance ID"
    ::= { gamMepConfigClientFlowEntry 1 }

gamMepConfigClientFlowFlowId OBJECT-TYPE
    SYNTAX      GAMInterfaceIndex
    MAX-ACCESS  accessible-for-notify
    STATUS      current
    DESCRIPTION
        "The Client Flow id - ifindex"
    ::= { gamMepConfigClientFlowEntry 2 }

gamMepConfigClientFlowAisPrio OBJECT-TYPE
    SYNTAX      GAMUnsigned8
    MAX-ACCESS  read-write
    STATUS      current
    DESCRIPTION
        "AIS Priority (EVC COS-ID) 0-7. Capability client_prio_highest indicate
         highest possible is requested"
    ::= { gamMepConfigClientFlowEntry 3 }

gamMepConfigClientFlowLckPrio OBJECT-TYPE
    SYNTAX      GAMUnsigned8
    MAX-ACCESS  read-write
    STATUS      current
    DESCRIPTION
        "LCK Priority (EVC COS-ID) 0-7. Capability client_prio_highest indicate
         highest possible is requested"
    ::= { gamMepConfigClientFlowEntry 4 }

gamMepConfigClientFlowLevel OBJECT-TYPE
    SYNTAX      GAMUnsigned8
    MAX-ACCESS  read-write
    STATUS      current
    DESCRIPTION
        "Client flow level"
    ::= { gamMepConfigClientFlowEntry 5 }

gamMepConfigClientFlowAction OBJECT-TYPE
    SYNTAX      GAMRowEditorState
    MAX-ACCESS  read-write
    STATUS      current
    DESCRIPTION
        "Action"
    ::= { gamMepConfigClientFlowEntry 100 }

gamMepConfigClientFlowRowEditor OBJECT IDENTIFIER
    ::= { gamMepConfigClient 3 }

gamMepConfigClientFlowRowEditorId OBJECT-TYPE
    SYNTAX      Integer32 (1..2147483647)
    MAX-ACCESS  read-write
    STATUS      current
    DESCRIPTION
        "The MEP instance ID"
    ::= { gamMepConfigClientFlowRowEditor 1 }

gamMepConfigClientFlowRowEditorFlowId OBJECT-TYPE
    SYNTAX      GAMInterfaceIndex
    MAX-ACCESS  read-write
    STATUS      current
    DESCRIPTION
        "The Client Flow id - ifindex"
    ::= { gamMepConfigClientFlowRowEditor 2 }

gamMepConfigClientFlowRowEditorAisPrio OBJECT-TYPE
    SYNTAX      GAMUnsigned8
    MAX-ACCESS  read-write
    STATUS      current
    DESCRIPTION
        "AIS Priority (EVC COS-ID) 0-7. Capability client_prio_highest indicate
         highest possible is requested"
    ::= { gamMepConfigClientFlowRowEditor 3 }

gamMepConfigClientFlowRowEditorLckPrio OBJECT-TYPE
    SYNTAX      GAMUnsigned8
    MAX-ACCESS  read-write
    STATUS      current
    DESCRIPTION
        "LCK Priority (EVC COS-ID) 0-7. Capability client_prio_highest indicate
         highest possible is requested"
    ::= { gamMepConfigClientFlowRowEditor 4 }

gamMepConfigClientFlowRowEditorLevel OBJECT-TYPE
    SYNTAX      GAMUnsigned8
    MAX-ACCESS  read-write
    STATUS      current
    DESCRIPTION
        "Client flow level"
    ::= { gamMepConfigClientFlowRowEditor 5 }

gamMepConfigClientFlowRowEditorAction OBJECT-TYPE
    SYNTAX      GAMRowEditorState
    MAX-ACCESS  read-write
    STATUS      current
    DESCRIPTION
        "Action"
    ::= { gamMepConfigClientFlowRowEditor 100 }

gamMepConfigSyslog OBJECT IDENTIFIER
    ::= { gamMepConfig 13 }

gamMepConfigSyslogTable OBJECT-TYPE
    SYNTAX      SEQUENCE OF GAMMepConfigSyslogEntry
    MAX-ACCESS  not-accessible
    STATUS      current
    DESCRIPTION
        "This is a table of created instance Syslog configuration parameters"
    ::= { gamMepConfigSyslog 1 }

gamMepConfigSyslogEntry OBJECT-TYPE
    SYNTAX      GAMMepConfigSyslogEntry
    MAX-ACCESS  not-accessible
    STATUS      current
    DESCRIPTION
        "This is a created instance Syslog configuration parameters"
    INDEX       { gamMepConfigSyslogId }
    ::= { gamMepConfigSyslogTable 1 }

GAMMepConfigSyslogEntry ::= SEQUENCE {
    gamMepConfigSyslogId      Integer32,
    gamMepConfigSyslogEnable  TruthValue
}

gamMepConfigSyslogId OBJECT-TYPE
    SYNTAX      Integer32 (1..2147483647)
    MAX-ACCESS  accessible-for-notify
    STATUS      current
    DESCRIPTION
        "The MEP instance ID"
    ::= { gamMepConfigSyslogEntry 1 }

gamMepConfigSyslogEnable OBJECT-TYPE
    SYNTAX      TruthValue
    MAX-ACCESS  read-write
    STATUS      current
    DESCRIPTION
        "The instance can enable generation of syslog entries "
    ::= { gamMepConfigSyslogEntry 2 }

gamMepConfigTlv OBJECT IDENTIFIER
    ::= { gamMepConfig 14 }

gamMepConfigTlvLeaf OBJECT IDENTIFIER
    ::= { gamMepConfigTlv 1 }

gamMepConfigTlvLeafOsTlvOuiFirst OBJECT-TYPE
    SYNTAX      GAMUnsigned8
    MAX-ACCESS  read-write
    STATUS      current
    DESCRIPTION
        "Transmitted OS TLV - The OUI content first nibble"
    ::= { gamMepConfigTlvLeaf 2 }

gamMepConfigTlvLeafOsTlvOuiSecond OBJECT-TYPE
    SYNTAX      GAMUnsigned8
    MAX-ACCESS  read-write
    STATUS      current
    DESCRIPTION
        "Transmitted OS TLV - The OUI content second nibble"
    ::= { gamMepConfigTlvLeaf 3 }

gamMepConfigTlvLeafOsTlvOuiThird OBJECT-TYPE
    SYNTAX      GAMUnsigned8
    MAX-ACCESS  read-write
    STATUS      current
    DESCRIPTION
        "Transmitted OS TLV - The OUI content third nibble"
    ::= { gamMepConfigTlvLeaf 4 }

gamMepConfigTlvLeafOsTlvSubType OBJECT-TYPE
    SYNTAX      GAMUnsigned8
    MAX-ACCESS  read-write
    STATUS      current
    DESCRIPTION
        "Transmitted OS TLV - The Sub-Type content"
    ::= { gamMepConfigTlvLeaf 5 }

gamMepConfigTlvLeafOsTlvValue OBJECT-TYPE
    SYNTAX      GAMUnsigned8
    MAX-ACCESS  read-write
    STATUS      current
    DESCRIPTION
        "Transmitted OS TLV - The Value content"
    ::= { gamMepConfigTlvLeaf 6 }

gamMepConfigBfd OBJECT IDENTIFIER
    ::= { gamMepConfig 15 }

gamMepConfigBfdTable OBJECT-TYPE
    SYNTAX      SEQUENCE OF GAMMepConfigBfdEntry
    MAX-ACCESS  not-accessible
    STATUS      current
    DESCRIPTION
        "This is a table of created instance Bidirectional Forwarding Detection
         configuration parameters"
    ::= { gamMepConfigBfd 1 }

gamMepConfigBfdEntry OBJECT-TYPE
    SYNTAX      GAMMepConfigBfdEntry
    MAX-ACCESS  not-accessible
    STATUS      current
    DESCRIPTION
        "This is a created instance Bidirectional Forwarding Detection
         configuration parameters."
    INDEX       { gamMepConfigBfdId }
    ::= { gamMepConfigBfdTable 1 }

GAMMepConfigBfdEntry ::= SEQUENCE {
    gamMepConfigBfdId             Integer32,
    gamMepConfigBfdEnable         TruthValue,
    gamMepConfigBfdIsIndependent  TruthValue,
    gamMepConfigBfdCcOnly         TruthValue,
    gamMepConfigBfdTxAuthEnabled  TruthValue,
    gamMepConfigBfdRxAuthEnabled  TruthValue,
    gamMepConfigBfdTxAuthKeyId    GAMUnsigned8,
    gamMepConfigBfdCcPeriod       Unsigned32,
    gamMepConfigBfdRxFlow         Unsigned32,
    gamMepConfigBfdAction         GAMRowEditorState
}

gamMepConfigBfdId OBJECT-TYPE
    SYNTAX      Integer32 (1..2147483647)
    MAX-ACCESS  accessible-for-notify
    STATUS      current
    DESCRIPTION
        "The MEP instance ID"
    ::= { gamMepConfigBfdEntry 1 }

gamMepConfigBfdEnable OBJECT-TYPE
    SYNTAX      TruthValue
    MAX-ACCESS  read-write
    STATUS      current
    DESCRIPTION
        "CC/CV transmission and LOC detection is enabled if true."
    ::= { gamMepConfigBfdEntry 2 }

gamMepConfigBfdIsIndependent OBJECT-TYPE
    SYNTAX      TruthValue
    MAX-ACCESS  read-write
    STATUS      current
    DESCRIPTION
        "Independent mode if true, coordinated if false."
    ::= { gamMepConfigBfdEntry 3 }

gamMepConfigBfdCcOnly OBJECT-TYPE
    SYNTAX      TruthValue
    MAX-ACCESS  read-write
    STATUS      current
    DESCRIPTION
        "Only transmit CC frames (no CV frames) if true."
    ::= { gamMepConfigBfdEntry 4 }

gamMepConfigBfdTxAuthEnabled OBJECT-TYPE
    SYNTAX      TruthValue
    MAX-ACCESS  read-write
    STATUS      current
    DESCRIPTION
        "Authentication enabled for transmission of CC/CV frames to peer if
         true."
    ::= { gamMepConfigBfdEntry 5 }

gamMepConfigBfdRxAuthEnabled OBJECT-TYPE
    SYNTAX      TruthValue
    MAX-ACCESS  read-write
    STATUS      current
    DESCRIPTION
        "Authentication enabled for reception of CC/CV frames from peer if true."
    ::= { gamMepConfigBfdEntry 6 }

gamMepConfigBfdTxAuthKeyId OBJECT-TYPE
    SYNTAX      GAMUnsigned8
    MAX-ACCESS  read-write
    STATUS      current
    DESCRIPTION
        "Authentication used for transmission of CC/CV frames to peer."
    ::= { gamMepConfigBfdEntry 7 }

gamMepConfigBfdCcPeriod OBJECT-TYPE
    SYNTAX      Unsigned32
    MAX-ACCESS  read-write
    STATUS      current
    DESCRIPTION
        "Desired CC transmission period in us, 1 us - 60 sec."
    ::= { gamMepConfigBfdEntry 8 }

gamMepConfigBfdRxFlow OBJECT-TYPE
    SYNTAX      Unsigned32
    MAX-ACCESS  read-write
    STATUS      current
    DESCRIPTION
        "Rx flow number (MPLS-TP link, MPLS-TP tunnel, MPLS-TP LSP or MPLS-TP
         Pseudo-Wire) for independent mode."
    ::= { gamMepConfigBfdEntry 9 }

gamMepConfigBfdAction OBJECT-TYPE
    SYNTAX      GAMRowEditorState
    MAX-ACCESS  read-write
    STATUS      current
    DESCRIPTION
        "Action"
    ::= { gamMepConfigBfdEntry 100 }

gamMepConfigBfdRowEditor OBJECT IDENTIFIER
    ::= { gamMepConfigBfd 2 }

gamMepConfigBfdRowEditorId OBJECT-TYPE
    SYNTAX      Integer32 (1..2147483647)
    MAX-ACCESS  read-write
    STATUS      current
    DESCRIPTION
        "The MEP instance ID"
    ::= { gamMepConfigBfdRowEditor 1 }

gamMepConfigBfdRowEditorEnable OBJECT-TYPE
    SYNTAX      TruthValue
    MAX-ACCESS  read-write
    STATUS      current
    DESCRIPTION
        "CC/CV transmission and LOC detection is enabled if true."
    ::= { gamMepConfigBfdRowEditor 2 }

gamMepConfigBfdRowEditorIsIndependent OBJECT-TYPE
    SYNTAX      TruthValue
    MAX-ACCESS  read-write
    STATUS      current
    DESCRIPTION
        "Independent mode if true, coordinated if false."
    ::= { gamMepConfigBfdRowEditor 3 }

gamMepConfigBfdRowEditorCcOnly OBJECT-TYPE
    SYNTAX      TruthValue
    MAX-ACCESS  read-write
    STATUS      current
    DESCRIPTION
        "Only transmit CC frames (no CV frames) if true."
    ::= { gamMepConfigBfdRowEditor 4 }

gamMepConfigBfdRowEditorTxAuthEnabled OBJECT-TYPE
    SYNTAX      TruthValue
    MAX-ACCESS  read-write
    STATUS      current
    DESCRIPTION
        "Authentication enabled for transmission of CC/CV frames to peer if
         true."
    ::= { gamMepConfigBfdRowEditor 5 }

gamMepConfigBfdRowEditorRxAuthEnabled OBJECT-TYPE
    SYNTAX      TruthValue
    MAX-ACCESS  read-write
    STATUS      current
    DESCRIPTION
        "Authentication enabled for reception of CC/CV frames from peer if true."
    ::= { gamMepConfigBfdRowEditor 6 }

gamMepConfigBfdRowEditorTxAuthKeyId OBJECT-TYPE
    SYNTAX      GAMUnsigned8
    MAX-ACCESS  read-write
    STATUS      current
    DESCRIPTION
        "Authentication used for transmission of CC/CV frames to peer."
    ::= { gamMepConfigBfdRowEditor 7 }

gamMepConfigBfdRowEditorCcPeriod OBJECT-TYPE
    SYNTAX      Unsigned32
    MAX-ACCESS  read-write
    STATUS      current
    DESCRIPTION
        "Desired CC transmission period in us, 1 us - 60 sec."
    ::= { gamMepConfigBfdRowEditor 8 }

gamMepConfigBfdRowEditorRxFlow OBJECT-TYPE
    SYNTAX      Unsigned32
    MAX-ACCESS  read-write
    STATUS      current
    DESCRIPTION
        "Rx flow number (MPLS-TP link, MPLS-TP tunnel, MPLS-TP LSP or MPLS-TP
         Pseudo-Wire) for independent mode."
    ::= { gamMepConfigBfdRowEditor 9 }

gamMepConfigBfdRowEditorAction OBJECT-TYPE
    SYNTAX      GAMRowEditorState
    MAX-ACCESS  read-write
    STATUS      current
    DESCRIPTION
        "Action"
    ::= { gamMepConfigBfdRowEditor 100 }

gamMepConfigBfdAuth OBJECT IDENTIFIER
    ::= { gamMepConfig 16 }

gamMepConfigBfdAuthTable OBJECT-TYPE
    SYNTAX      SEQUENCE OF GAMMepConfigBfdAuthEntry
    MAX-ACCESS  not-accessible
    STATUS      current
    DESCRIPTION
        "This is a table of created instance Bidirectional Forwarding Detection
         Authentication configuration parameters"
    ::= { gamMepConfigBfdAuth 1 }

gamMepConfigBfdAuthEntry OBJECT-TYPE
    SYNTAX      GAMMepConfigBfdAuthEntry
    MAX-ACCESS  not-accessible
    STATUS      current
    DESCRIPTION
        "This is a created instance Bidirectional Forwarding Detection
         Authentication configuration parameters."
    INDEX       { gamMepConfigBfdAuthId }
    ::= { gamMepConfigBfdAuthTable 1 }

GAMMepConfigBfdAuthEntry ::= SEQUENCE {
    gamMepConfigBfdAuthId       Integer32,
    gamMepConfigBfdAuthKeyType  GAMMepBfdAuthenticationType,
    gamMepConfigBfdAuthKeyLen   GAMUnsigned8,
    gamMepConfigBfdAuthKey      OCTET STRING,
    gamMepConfigBfdAuthAction   GAMRowEditorState
}

gamMepConfigBfdAuthId OBJECT-TYPE
    SYNTAX      Integer32 (0..255)
    MAX-ACCESS  accessible-for-notify
    STATUS      current
    DESCRIPTION
        "The Bfd Auth Key instance ID"
    ::= { gamMepConfigBfdAuthEntry 1 }

gamMepConfigBfdAuthKeyType OBJECT-TYPE
    SYNTAX      GAMMepBfdAuthenticationType
    MAX-ACCESS  read-write
    STATUS      current
    DESCRIPTION
        "Key type."
    ::= { gamMepConfigBfdAuthEntry 2 }

gamMepConfigBfdAuthKeyLen OBJECT-TYPE
    SYNTAX      GAMUnsigned8
    MAX-ACCESS  read-write
    STATUS      current
    DESCRIPTION
        "Key length in bytes. 1-16 for Simple Password, 16 for MD5 and 20 for
         SHA1."
    ::= { gamMepConfigBfdAuthEntry 3 }

gamMepConfigBfdAuthKey OBJECT-TYPE
    SYNTAX      OCTET STRING (SIZE(20))
    MAX-ACCESS  read-write
    STATUS      current
    DESCRIPTION
        "Key value."
    ::= { gamMepConfigBfdAuthEntry 4 }

gamMepConfigBfdAuthAction OBJECT-TYPE
    SYNTAX      GAMRowEditorState
    MAX-ACCESS  read-write
    STATUS      current
    DESCRIPTION
        "Action"
    ::= { gamMepConfigBfdAuthEntry 100 }

gamMepConfigBfdAuthRowEditor OBJECT IDENTIFIER
    ::= { gamMepConfigBfdAuth 2 }

gamMepConfigBfdAuthRowEditorId OBJECT-TYPE
    SYNTAX      Integer32 (0..255)
    MAX-ACCESS  read-write
    STATUS      current
    DESCRIPTION
        "The Bfd Auth Key instance ID"
    ::= { gamMepConfigBfdAuthRowEditor 1 }

gamMepConfigBfdAuthRowEditorKeyType OBJECT-TYPE
    SYNTAX      GAMMepBfdAuthenticationType
    MAX-ACCESS  read-write
    STATUS      current
    DESCRIPTION
        "Key type."
    ::= { gamMepConfigBfdAuthRowEditor 2 }

gamMepConfigBfdAuthRowEditorKeyLen OBJECT-TYPE
    SYNTAX      GAMUnsigned8
    MAX-ACCESS  read-write
    STATUS      current
    DESCRIPTION
        "Key length in bytes. 1-16 for Simple Password, 16 for MD5 and 20 for
         SHA1."
    ::= { gamMepConfigBfdAuthRowEditor 3 }

gamMepConfigBfdAuthRowEditorKey OBJECT-TYPE
    SYNTAX      OCTET STRING (SIZE(20))
    MAX-ACCESS  read-write
    STATUS      current
    DESCRIPTION
        "Key value."
    ::= { gamMepConfigBfdAuthRowEditor 4 }

gamMepConfigBfdAuthRowEditorAction OBJECT-TYPE
    SYNTAX      GAMRowEditorState
    MAX-ACCESS  read-write
    STATUS      current
    DESCRIPTION
        "Action"
    ::= { gamMepConfigBfdAuthRowEditor 100 }

gamMepConfigRt OBJECT IDENTIFIER
    ::= { gamMepConfig 17 }

gamMepConfigRtTable OBJECT-TYPE
    SYNTAX      SEQUENCE OF GAMMepConfigRtEntry
    MAX-ACCESS  not-accessible
    STATUS      current
    DESCRIPTION
        "This is a table of created instance Route Trace configuration
         parameters"
    ::= { gamMepConfigRt 1 }

gamMepConfigRtEntry OBJECT-TYPE
    SYNTAX      GAMMepConfigRtEntry
    MAX-ACCESS  not-accessible
    STATUS      current
    DESCRIPTION
        "This is a created instance Route Trace configuration parameters."
    INDEX       { gamMepConfigRtId }
    ::= { gamMepConfigRtTable 1 }

GAMMepConfigRtEntry ::= SEQUENCE {
    gamMepConfigRtId             Integer32,
    gamMepConfigRtTrafficClass   GAMUnsigned8,
    gamMepConfigRtSrcIdTlv       TruthValue,
    gamMepConfigRtDstIdTlv       TruthValue,
    gamMepConfigRtPadTlvType     GAMMepRtPadTlvType,
    gamMepConfigRtPadTlvLen      GAMUnsigned16,
    gamMepConfigRtFlags          GAMUnsigned8,
    gamMepConfigRtMaxTimeToLive  GAMUnsigned8,
    gamMepConfigRtAction         GAMRowEditorState
}

gamMepConfigRtId OBJECT-TYPE
    SYNTAX      Integer32 (1..2147483647)
    MAX-ACCESS  accessible-for-notify
    STATUS      current
    DESCRIPTION
        "The MEP instance ID"
    ::= { gamMepConfigRtEntry 1 }

gamMepConfigRtTrafficClass OBJECT-TYPE
    SYNTAX      GAMUnsigned8
    MAX-ACCESS  read-write
    STATUS      current
    DESCRIPTION
        "Traffic class value used in the transmitted RT request PDU. Range 0 to
         7"
    ::= { gamMepConfigRtEntry 2 }

gamMepConfigRtSrcIdTlv OBJECT-TYPE
    SYNTAX      TruthValue
    MAX-ACCESS  read-write
    STATUS      current
    DESCRIPTION
        "Include Source ID TLV in the RT request"
    ::= { gamMepConfigRtEntry 3 }

gamMepConfigRtDstIdTlv OBJECT-TYPE
    SYNTAX      TruthValue
    MAX-ACCESS  read-write
    STATUS      current
    DESCRIPTION
        "Include Destination ID TLV in the RT request"
    ::= { gamMepConfigRtEntry 4 }

gamMepConfigRtPadTlvType OBJECT-TYPE
    SYNTAX      GAMMepRtPadTlvType
    MAX-ACCESS  read-write
    STATUS      current
    DESCRIPTION
        "Pad TLV type"
    ::= { gamMepConfigRtEntry 5 }

gamMepConfigRtPadTlvLen OBJECT-TYPE
    SYNTAX      GAMUnsigned16
    MAX-ACCESS  read-write
    STATUS      current
    DESCRIPTION
        "Pad TLV data length. Range 1 to 1024."
    ::= { gamMepConfigRtEntry 6 }

gamMepConfigRtFlags OBJECT-TYPE
    SYNTAX      GAMUnsigned8
    MAX-ACCESS  read-write
    STATUS      current
    DESCRIPTION
        "Flags for RT request. Bit 0: V flag (Validate FEC stack), bit 1: T flag
         (Respond Only If TTL Expired), bit 2: R flag (Validate Reverse Path)"
    ::= { gamMepConfigRtEntry 7 }

gamMepConfigRtMaxTimeToLive OBJECT-TYPE
    SYNTAX      GAMUnsigned8
    MAX-ACCESS  read-write
    STATUS      current
    DESCRIPTION
        "Max. Time To Live for RT request."
    ::= { gamMepConfigRtEntry 8 }

gamMepConfigRtAction OBJECT-TYPE
    SYNTAX      GAMRowEditorState
    MAX-ACCESS  read-write
    STATUS      current
    DESCRIPTION
        "Action"
    ::= { gamMepConfigRtEntry 100 }

gamMepConfigRtRowEditor OBJECT IDENTIFIER
    ::= { gamMepConfigRt 2 }

gamMepConfigRtRowEditorId OBJECT-TYPE
    SYNTAX      Integer32 (1..2147483647)
    MAX-ACCESS  read-write
    STATUS      current
    DESCRIPTION
        "The MEP instance ID"
    ::= { gamMepConfigRtRowEditor 1 }

gamMepConfigRtRowEditorTrafficClass OBJECT-TYPE
    SYNTAX      GAMUnsigned8
    MAX-ACCESS  read-write
    STATUS      current
    DESCRIPTION
        "Traffic class value used in the transmitted RT request PDU. Range 0 to
         7"
    ::= { gamMepConfigRtRowEditor 2 }

gamMepConfigRtRowEditorSrcIdTlv OBJECT-TYPE
    SYNTAX      TruthValue
    MAX-ACCESS  read-write
    STATUS      current
    DESCRIPTION
        "Include Source ID TLV in the RT request"
    ::= { gamMepConfigRtRowEditor 3 }

gamMepConfigRtRowEditorDstIdTlv OBJECT-TYPE
    SYNTAX      TruthValue
    MAX-ACCESS  read-write
    STATUS      current
    DESCRIPTION
        "Include Destination ID TLV in the RT request"
    ::= { gamMepConfigRtRowEditor 4 }

gamMepConfigRtRowEditorPadTlvType OBJECT-TYPE
    SYNTAX      GAMMepRtPadTlvType
    MAX-ACCESS  read-write
    STATUS      current
    DESCRIPTION
        "Pad TLV type"
    ::= { gamMepConfigRtRowEditor 5 }

gamMepConfigRtRowEditorPadTlvLen OBJECT-TYPE
    SYNTAX      GAMUnsigned16
    MAX-ACCESS  read-write
    STATUS      current
    DESCRIPTION
        "Pad TLV data length. Range 1 to 1024."
    ::= { gamMepConfigRtRowEditor 6 }

gamMepConfigRtRowEditorFlags OBJECT-TYPE
    SYNTAX      GAMUnsigned8
    MAX-ACCESS  read-write
    STATUS      current
    DESCRIPTION
        "Flags for RT request. Bit 0: V flag (Validate FEC stack), bit 1: T flag
         (Respond Only If TTL Expired), bit 2: R flag (Validate Reverse Path)"
    ::= { gamMepConfigRtRowEditor 7 }

gamMepConfigRtRowEditorMaxTimeToLive OBJECT-TYPE
    SYNTAX      GAMUnsigned8
    MAX-ACCESS  read-write
    STATUS      current
    DESCRIPTION
        "Max. Time To Live for RT request."
    ::= { gamMepConfigRtRowEditor 8 }

gamMepConfigRtRowEditorAction OBJECT-TYPE
    SYNTAX      GAMRowEditorState
    MAX-ACCESS  read-write
    STATUS      current
    DESCRIPTION
        "Action"
    ::= { gamMepConfigRtRowEditor 100 }

gamMepConfigLst OBJECT IDENTIFIER
    ::= { gamMepConfig 18 }

gamMepConfigLstTable OBJECT-TYPE
    SYNTAX      SEQUENCE OF GAMMepConfigLstEntry
    MAX-ACCESS  not-accessible
    STATUS      current
    DESCRIPTION
        "This is a table of created instance Link State Tracking configuration
         parameters"
    ::= { gamMepConfigLst 1 }

gamMepConfigLstEntry OBJECT-TYPE
    SYNTAX      GAMMepConfigLstEntry
    MAX-ACCESS  not-accessible
    STATUS      current
    DESCRIPTION
        "This is a created instance Link State Tracking configuration parameters"
    INDEX       { gamMepConfigLstId }
    ::= { gamMepConfigLstTable 1 }

GAMMepConfigLstEntry ::= SEQUENCE {
    gamMepConfigLstId      Integer32,
    gamMepConfigLstEnable  TruthValue
}

gamMepConfigLstId OBJECT-TYPE
    SYNTAX      Integer32 (1..2147483647)
    MAX-ACCESS  accessible-for-notify
    STATUS      current
    DESCRIPTION
        "The MEP instance ID"
    ::= { gamMepConfigLstEntry 1 }

gamMepConfigLstEnable OBJECT-TYPE
    SYNTAX      TruthValue
    MAX-ACCESS  read-write
    STATUS      current
    DESCRIPTION
        "The instance can enable Link State Tracking. When LST is enabled, Local
         SF or received 'isDown' in CCM Interface Status TLV, will bring down
         the residence port. Only valid in Up-MEP."
    ::= { gamMepConfigLstEntry 2 }

gamMepConfigLmAvail OBJECT IDENTIFIER
    ::= { gamMepConfig 19 }

gamMepConfigLmAvailTable OBJECT-TYPE
    SYNTAX      SEQUENCE OF GAMMepConfigLmAvailEntry
    MAX-ACCESS  not-accessible
    STATUS      current
    DESCRIPTION
        "This is a table of created instance Loss Measurement Availability
         configuration parameters"
    ::= { gamMepConfigLmAvail 1 }

gamMepConfigLmAvailEntry OBJECT-TYPE
    SYNTAX      GAMMepConfigLmAvailEntry
    MAX-ACCESS  not-accessible
    STATUS      current
    DESCRIPTION
        "This is a created instance Loss Measurement Availability parameters."
    INDEX       { gamMepConfigLmAvailId }
    ::= { gamMepConfigLmAvailTable 1 }

GAMMepConfigLmAvailEntry ::= SEQUENCE {
    gamMepConfigLmAvailId           Integer32,
    gamMepConfigLmAvailEnable       TruthValue,
    gamMepConfigLmAvailLosRatioThr  Unsigned32,
    gamMepConfigLmAvailInterval     Unsigned32,
    gamMepConfigLmAvailMaintenance  TruthValue
}

gamMepConfigLmAvailId OBJECT-TYPE
    SYNTAX      Integer32 (1..2147483647)
    MAX-ACCESS  accessible-for-notify
    STATUS      current
    DESCRIPTION
        "The MEP instance ID"
    ::= { gamMepConfigLmAvailEntry 1 }

gamMepConfigLmAvailEnable OBJECT-TYPE
    SYNTAX      TruthValue
    MAX-ACCESS  read-write
    STATUS      current
    DESCRIPTION
        "Loss Measurement Availability is enabled"
    ::= { gamMepConfigLmAvailEntry 2 }

gamMepConfigLmAvailLosRatioThr OBJECT-TYPE
    SYNTAX      Unsigned32
    MAX-ACCESS  read-write
    STATUS      current
    DESCRIPTION
        "Availability frame loss ratio threshold in per mille."
    ::= { gamMepConfigLmAvailEntry 3 }

gamMepConfigLmAvailInterval OBJECT-TYPE
    SYNTAX      Unsigned32
    MAX-ACCESS  read-write
    STATUS      current
    DESCRIPTION
        "Availability interval - number of measurements with same availability
         in order to change Availability state. The valid range is 1 to 1000."
    ::= { gamMepConfigLmAvailEntry 4 }

gamMepConfigLmAvailMaintenance OBJECT-TYPE
    SYNTAX      TruthValue
    MAX-ACCESS  read-write
    STATUS      current
    DESCRIPTION
        "Loss Measurement Availability Maintenance enable/disable"
    ::= { gamMepConfigLmAvailEntry 5 }

gamMepConfigLmHli OBJECT IDENTIFIER
    ::= { gamMepConfig 20 }

gamMepConfigLmHliTable OBJECT-TYPE
    SYNTAX      SEQUENCE OF GAMMepConfigLmHliEntry
    MAX-ACCESS  not-accessible
    STATUS      current
    DESCRIPTION
        "This is a table of created instance Loss Measurement High Loss Interval
         configuration parameters"
    ::= { gamMepConfigLmHli 1 }

gamMepConfigLmHliEntry OBJECT-TYPE
    SYNTAX      GAMMepConfigLmHliEntry
    MAX-ACCESS  not-accessible
    STATUS      current
    DESCRIPTION
        "This is a created instance Loss Measurement High Loss Interval
         parameters."
    INDEX       { gamMepConfigLmHliId }
    ::= { gamMepConfigLmHliTable 1 }

GAMMepConfigLmHliEntry ::= SEQUENCE {
    gamMepConfigLmHliId                Integer32,
    gamMepConfigLmHliEnable            TruthValue,
    gamMepConfigLmHliHiLosRatioThr     Unsigned32,
    gamMepConfigLmHliConInterval       Unsigned32,
    gamMepConfigLmHliCntHolddownTimer  Unsigned32
}

gamMepConfigLmHliId OBJECT-TYPE
    SYNTAX      Integer32 (1..2147483647)
    MAX-ACCESS  accessible-for-notify
    STATUS      current
    DESCRIPTION
        "The MEP instance ID"
    ::= { gamMepConfigLmHliEntry 1 }

gamMepConfigLmHliEnable OBJECT-TYPE
    SYNTAX      TruthValue
    MAX-ACCESS  read-write
    STATUS      current
    DESCRIPTION
        "Loss Measurement High Loss Interval is enabled"
    ::= { gamMepConfigLmHliEntry 2 }

gamMepConfigLmHliHiLosRatioThr OBJECT-TYPE
    SYNTAX      Unsigned32
    MAX-ACCESS  read-write
    STATUS      current
    DESCRIPTION
        "High Loss Interval frame loss ratio threshold in per mille."
    ::= { gamMepConfigLmHliEntry 3 }

gamMepConfigLmHliConInterval OBJECT-TYPE
    SYNTAX      Unsigned32
    MAX-ACCESS  read-write
    STATUS      current
    DESCRIPTION
        "High Loss Interval consecutive interval (number of measurements)."
    ::= { gamMepConfigLmHliEntry 4 }

gamMepConfigLmHliCntHolddownTimer OBJECT-TYPE
    SYNTAX      Unsigned32
    MAX-ACCESS  read-write
    STATUS      current
    DESCRIPTION
        "Holddown timer in seconds for JSON notification updates for High Loss
         Interval NearEndCnt and FarEndCnt."
    ::= { gamMepConfigLmHliEntry 5 }

gamMepConfigLmSdeg OBJECT IDENTIFIER
    ::= { gamMepConfig 21 }

gamMepConfigLmSdegTable OBJECT-TYPE
    SYNTAX      SEQUENCE OF GAMMepConfigLmSdegEntry
    MAX-ACCESS  not-accessible
    STATUS      current
    DESCRIPTION
        "This is a table of created instance Loss Measurement Signal Degrade
         configuration parameters"
    ::= { gamMepConfigLmSdeg 1 }

gamMepConfigLmSdegEntry OBJECT-TYPE
    SYNTAX      GAMMepConfigLmSdegEntry
    MAX-ACCESS  not-accessible
    STATUS      current
    DESCRIPTION
        "This is a created instance Loss Measurement Signal Degrade parameters."
    INDEX       { gamMepConfigLmSdegId }
    ::= { gamMepConfigLmSdegTable 1 }

GAMMepConfigLmSdegEntry ::= SEQUENCE {
    gamMepConfigLmSdegId           Integer32,
    gamMepConfigLmSdegEnable       TruthValue,
    gamMepConfigLmSdegTxMin        Unsigned32,
    gamMepConfigLmSdegLosRatioThr  Unsigned32,
    gamMepConfigLmSdegBadThr       Unsigned32,
    gamMepConfigLmSdegGoodThr      Unsigned32
}

gamMepConfigLmSdegId OBJECT-TYPE
    SYNTAX      Integer32 (1..2147483647)
    MAX-ACCESS  accessible-for-notify
    STATUS      current
    DESCRIPTION
        "The MEP instance ID"
    ::= { gamMepConfigLmSdegEntry 1 }

gamMepConfigLmSdegEnable OBJECT-TYPE
    SYNTAX      TruthValue
    MAX-ACCESS  read-write
    STATUS      current
    DESCRIPTION
        "Loss Measurement Signal Degrade is enabled"
    ::= { gamMepConfigLmSdegEntry 2 }

gamMepConfigLmSdegTxMin OBJECT-TYPE
    SYNTAX      Unsigned32
    MAX-ACCESS  read-write
    STATUS      current
    DESCRIPTION
        "Minimum number of frames that must be transmitted in a measurement
         before frame loss ratio is tested against LosRatioThr."
    ::= { gamMepConfigLmSdegEntry 3 }

gamMepConfigLmSdegLosRatioThr OBJECT-TYPE
    SYNTAX      Unsigned32
    MAX-ACCESS  read-write
    STATUS      current
    DESCRIPTION
        "Signal Degraded frame loss ratio threshold in per mille."
    ::= { gamMepConfigLmSdegEntry 4 }

gamMepConfigLmSdegBadThr OBJECT-TYPE
    SYNTAX      Unsigned32
    MAX-ACCESS  read-write
    STATUS      current
    DESCRIPTION
        "Number of consecutive bad interval measurements required to set degrade
         state."
    ::= { gamMepConfigLmSdegEntry 5 }

gamMepConfigLmSdegGoodThr OBJECT-TYPE
    SYNTAX      Unsigned32
    MAX-ACCESS  read-write
    STATUS      current
    DESCRIPTION
        "Number of consecutive good interval measurements required to clear
         degrade state."
    ::= { gamMepConfigLmSdegEntry 6 }

gamMepStatus OBJECT IDENTIFIER
    ::= { gamMepMibObjects 3 }

gamMepStatusInstance OBJECT IDENTIFIER
    ::= { gamMepStatus 1 }

gamMepStatusInstanceTable OBJECT-TYPE
    SYNTAX      SEQUENCE OF GAMMepStatusInstanceEntry
    MAX-ACCESS  not-accessible
    STATUS      current
    DESCRIPTION
        "This is a table of created instance status"
    ::= { gamMepStatusInstance 1 }

gamMepStatusInstanceEntry OBJECT-TYPE
    SYNTAX      GAMMepStatusInstanceEntry
    MAX-ACCESS  not-accessible
    STATUS      current
    DESCRIPTION
        "This is a created instance status"
    INDEX       { gamMepStatusInstanceId }
    ::= { gamMepStatusInstanceTable 1 }

GAMMepStatusInstanceEntry ::= SEQUENCE {
    gamMepStatusInstanceId         Integer32,
    gamMepStatusInstanceClevel     TruthValue,
    gamMepStatusInstanceCmeg       TruthValue,
    gamMepStatusInstanceCmep       TruthValue,
    gamMepStatusInstanceCssf       TruthValue,
    gamMepStatusInstanceCais       TruthValue,
    gamMepStatusInstanceClck       TruthValue,
    gamMepStatusInstanceAtsf       TruthValue,
    gamMepStatusInstanceAtsd       TruthValue,
    gamMepStatusInstanceAblk       TruthValue,
    gamMepStatusInstanceCloop      TruthValue,
    gamMepStatusInstanceCconfig    TruthValue,
    gamMepStatusInstanceCdeg       TruthValue,
    gamMepStatusInstanceOperState  GAMMepOperState
}

gamMepStatusInstanceId OBJECT-TYPE
    SYNTAX      Integer32 (1..2147483647)
    MAX-ACCESS  accessible-for-notify
    STATUS      current
    DESCRIPTION
        "The MEP instance ID"
    ::= { gamMepStatusInstanceEntry 1 }

gamMepStatusInstanceClevel OBJECT-TYPE
    SYNTAX      TruthValue
    MAX-ACCESS  read-only
    STATUS      current
    DESCRIPTION
        "Incorrect CCM level received"
    ::= { gamMepStatusInstanceEntry 2 }

gamMepStatusInstanceCmeg OBJECT-TYPE
    SYNTAX      TruthValue
    MAX-ACCESS  read-only
    STATUS      current
    DESCRIPTION
        "Incorrect CCM MEG id received"
    ::= { gamMepStatusInstanceEntry 3 }

gamMepStatusInstanceCmep OBJECT-TYPE
    SYNTAX      TruthValue
    MAX-ACCESS  read-only
    STATUS      current
    DESCRIPTION
        "Incorrect CCM MEP id received"
    ::= { gamMepStatusInstanceEntry 4 }

gamMepStatusInstanceCssf OBJECT-TYPE
    SYNTAX      TruthValue
    MAX-ACCESS  read-only
    STATUS      current
    DESCRIPTION
        "SSF state"
    ::= { gamMepStatusInstanceEntry 5 }

gamMepStatusInstanceCais OBJECT-TYPE
    SYNTAX      TruthValue
    MAX-ACCESS  read-only
    STATUS      current
    DESCRIPTION
        "AIS state. AIS is received."
    ::= { gamMepStatusInstanceEntry 6 }

gamMepStatusInstanceClck OBJECT-TYPE
    SYNTAX      TruthValue
    MAX-ACCESS  read-only
    STATUS      current
    DESCRIPTION
        "Locked State. LCK is received."
    ::= { gamMepStatusInstanceEntry 7 }

gamMepStatusInstanceAtsf OBJECT-TYPE
    SYNTAX      TruthValue
    MAX-ACCESS  read-only
    STATUS      current
    DESCRIPTION
        "Trail Signal fail consequent action is calculated"
    ::= { gamMepStatusInstanceEntry 8 }

gamMepStatusInstanceAtsd OBJECT-TYPE
    SYNTAX      TruthValue
    MAX-ACCESS  read-only
    STATUS      current
    DESCRIPTION
        "Trail Signal degrade consequent action is calculated"
    ::= { gamMepStatusInstanceEntry 9 }

gamMepStatusInstanceAblk OBJECT-TYPE
    SYNTAX      TruthValue
    MAX-ACCESS  read-only
    STATUS      current
    DESCRIPTION
        "Block consequent action is calculated"
    ::= { gamMepStatusInstanceEntry 10 }

gamMepStatusInstanceCloop OBJECT-TYPE
    SYNTAX      TruthValue
    MAX-ACCESS  read-only
    STATUS      current
    DESCRIPTION
        "Loop is detected. CCM is received with own MEP ID and SMAC."
    ::= { gamMepStatusInstanceEntry 11 }

gamMepStatusInstanceCconfig OBJECT-TYPE
    SYNTAX      TruthValue
    MAX-ACCESS  read-only
    STATUS      current
    DESCRIPTION
        "Configuration error detected. CCM is received with own MEP ID."
    ::= { gamMepStatusInstanceEntry 12 }

gamMepStatusInstanceCdeg OBJECT-TYPE
    SYNTAX      TruthValue
    MAX-ACCESS  read-only
    STATUS      current
    DESCRIPTION
        "Signal Degraded."
    ::= { gamMepStatusInstanceEntry 13 }

gamMepStatusInstanceOperState OBJECT-TYPE
    SYNTAX      GAMMepOperState
    MAX-ACCESS  read-only
    STATUS      current
    DESCRIPTION
        "Operational State.
         
         'operStateUp' The instance is UP meaning it is physically configured
         and operational.
         
         'operStateDown' The instance is DOWN meaning it is NOT physically
         configured and operational.
         
         'operStateDownInvalidConf' The instance is DOWN due to invalid
         configuration.
         
         'operStateDownfailingOamHw' The instance is DOWN due to failing OAM
         supporting HW resources.
         
         'operStateDownfailingMce' The instance is DOWN due to failing MCE
         resources."
    ::= { gamMepStatusInstanceEntry 14 }

gamMepStatusInstancePeerTable OBJECT-TYPE
    SYNTAX      SEQUENCE OF GAMMepStatusInstancePeerEntry
    MAX-ACCESS  not-accessible
    STATUS      current
    DESCRIPTION
        "This is a table of peer MEP status"
    ::= { gamMepStatusInstance 2 }

gamMepStatusInstancePeerEntry OBJECT-TYPE
    SYNTAX      GAMMepStatusInstancePeerEntry
    MAX-ACCESS  not-accessible
    STATUS      current
    DESCRIPTION
        "This is a peer MEP status"
    INDEX       { gamMepStatusInstancePeerId,
                  gamMepStatusInstancePeerPeerId }
    ::= { gamMepStatusInstancePeerTable 1 }

GAMMepStatusInstancePeerEntry ::= SEQUENCE {
    gamMepStatusInstancePeerId       Integer32,
    gamMepStatusInstancePeerPeerId   Integer32,
    gamMepStatusInstancePeerCloc     TruthValue,
    gamMepStatusInstancePeerCrdi     TruthValue,
    gamMepStatusInstancePeerCperiod  TruthValue,
    gamMepStatusInstancePeerCprio    TruthValue
}

gamMepStatusInstancePeerId OBJECT-TYPE
    SYNTAX      Integer32 (1..2147483647)
    MAX-ACCESS  accessible-for-notify
    STATUS      current
    DESCRIPTION
        "The MEP instance ID"
    ::= { gamMepStatusInstancePeerEntry 1 }

gamMepStatusInstancePeerPeerId OBJECT-TYPE
    SYNTAX      Integer32 (0..2147483647)
    MAX-ACCESS  accessible-for-notify
    STATUS      current
    DESCRIPTION
        "The Peer MEP ID"
    ::= { gamMepStatusInstancePeerEntry 2 }

gamMepStatusInstancePeerCloc OBJECT-TYPE
    SYNTAX      TruthValue
    MAX-ACCESS  read-only
    STATUS      current
    DESCRIPTION
        "CCM LOC state from peer MEP"
    ::= { gamMepStatusInstancePeerEntry 3 }

gamMepStatusInstancePeerCrdi OBJECT-TYPE
    SYNTAX      TruthValue
    MAX-ACCESS  read-only
    STATUS      current
    DESCRIPTION
        "CCM RDI state from peer MEP"
    ::= { gamMepStatusInstancePeerEntry 4 }

gamMepStatusInstancePeerCperiod OBJECT-TYPE
    SYNTAX      TruthValue
    MAX-ACCESS  read-only
    STATUS      current
    DESCRIPTION
        "CCM Period state from peer MEP"
    ::= { gamMepStatusInstancePeerEntry 5 }

gamMepStatusInstancePeerCprio OBJECT-TYPE
    SYNTAX      TruthValue
    MAX-ACCESS  read-only
    STATUS      current
    DESCRIPTION
        "CCM Priority state from peer MEP"
    ::= { gamMepStatusInstancePeerEntry 6 }

gamMepStatusLm OBJECT IDENTIFIER
    ::= { gamMepStatus 2 }

gamMepStatusLmTable OBJECT-TYPE
    SYNTAX      SEQUENCE OF GAMMepStatusLmEntry
    MAX-ACCESS  not-accessible
    STATUS      current
    DESCRIPTION
        "This table show the status of a Loss Measurement session between this
         MEP and its first peer MEP.
         
         This table is deprecated as it only show the status for the first peer
         MEP. It is thus not suitable when using Synthetic Loss Measurement
         since this option allow for multiple peers. Use the
         MepStatusLmPeerTable instead."
    ::= { gamMepStatusLm 1 }

gamMepStatusLmEntry OBJECT-TYPE
    SYNTAX      GAMMepStatusLmEntry
    MAX-ACCESS  not-accessible
    STATUS      current
    DESCRIPTION
        "This is a Loss Measurement status"
    INDEX       { gamMepStatusLmId }
    ::= { gamMepStatusLmTable 1 }

GAMMepStatusLmEntry ::= SEQUENCE {
    gamMepStatusLmId                    Integer32,
    gamMepStatusLmTxCounter             Unsigned32,
    gamMepStatusLmRxCounter             Unsigned32,
    gamMepStatusLmNearEndLosCounterTot  Integer32,
    gamMepStatusLmFarEndLosCounterTot   Integer32,
    gamMepStatusLmNearEndLosRatioInt    Unsigned32,
    gamMepStatusLmFarEndLosRatioInt     Unsigned32,
    gamMepStatusLmNearEndLosCounterInt  Unsigned32,
    gamMepStatusLmFarEndLosCounterInt   Unsigned32,
    gamMepStatusLmNearEndLosThCnt       Unsigned32,
    gamMepStatusLmFarEndLosThCnt        Unsigned32,
    gamMepStatusLmNearEndLosRatioTot    Unsigned32,
    gamMepStatusLmFarEndLosRatioTot     Unsigned32,
    gamMepStatusLmNearEndLosRatioMin    Unsigned32,
    gamMepStatusLmFarEndLosRatioMin     Unsigned32,
    gamMepStatusLmNearEndLosRatioMax    Unsigned32,
    gamMepStatusLmFarEndLosRatioMax     Unsigned32,
    gamMepStatusLmElapsedIntervals      Unsigned32
}

gamMepStatusLmId OBJECT-TYPE
    SYNTAX      Integer32 (1..2147483647)
    MAX-ACCESS  accessible-for-notify
    STATUS      current
    DESCRIPTION
        "The MEP instance ID"
    ::= { gamMepStatusLmEntry 1 }

gamMepStatusLmTxCounter OBJECT-TYPE
    SYNTAX      Unsigned32
    MAX-ACCESS  read-only
    STATUS      current
    DESCRIPTION
        "Transmitted PDU (LMM - CCM) containing counters."
    ::= { gamMepStatusLmEntry 2 }

gamMepStatusLmRxCounter OBJECT-TYPE
    SYNTAX      Unsigned32
    MAX-ACCESS  read-only
    STATUS      current
    DESCRIPTION
        "Received PDU (LMM - CCM) containing counters."
    ::= { gamMepStatusLmEntry 3 }

gamMepStatusLmNearEndLosCounterTot OBJECT-TYPE
    SYNTAX      Integer32
    MAX-ACCESS  read-only
    STATUS      current
    DESCRIPTION
        "Near end total frame loss counter."
    ::= { gamMepStatusLmEntry 4 }

gamMepStatusLmFarEndLosCounterTot OBJECT-TYPE
    SYNTAX      Integer32
    MAX-ACCESS  read-only
    STATUS      current
    DESCRIPTION
        "Far end total frame loss counter."
    ::= { gamMepStatusLmEntry 5 }

gamMepStatusLmNearEndLosRatioInt OBJECT-TYPE
    SYNTAX      Unsigned32
    MAX-ACCESS  read-only
    STATUS      current
    DESCRIPTION
        "Near end frame loss ratio for interval in per mille."
    ::= { gamMepStatusLmEntry 6 }

gamMepStatusLmFarEndLosRatioInt OBJECT-TYPE
    SYNTAX      Unsigned32
    MAX-ACCESS  read-only
    STATUS      current
    DESCRIPTION
        "Far end frame loss ratio for interval in per mille."
    ::= { gamMepStatusLmEntry 7 }

gamMepStatusLmNearEndLosCounterInt OBJECT-TYPE
    SYNTAX      Unsigned32
    MAX-ACCESS  read-only
    STATUS      current
    DESCRIPTION
        "Number of measurements that has contributed to near end loss (since
         last clear)."
    ::= { gamMepStatusLmEntry 8 }

gamMepStatusLmFarEndLosCounterInt OBJECT-TYPE
    SYNTAX      Unsigned32
    MAX-ACCESS  read-only
    STATUS      current
    DESCRIPTION
        "Number of measurements that has contributed to far end loss (since last
         clear)."
    ::= { gamMepStatusLmEntry 9 }

gamMepStatusLmNearEndLosThCnt OBJECT-TYPE
    SYNTAX      Unsigned32
    MAX-ACCESS  read-only
    STATUS      current
    DESCRIPTION
        "Near end frame loss threshold count."
    ::= { gamMepStatusLmEntry 10 }

gamMepStatusLmFarEndLosThCnt OBJECT-TYPE
    SYNTAX      Unsigned32
    MAX-ACCESS  read-only
    STATUS      current
    DESCRIPTION
        "Far end frame loss threshold count."
    ::= { gamMepStatusLmEntry 11 }

gamMepStatusLmNearEndLosRatioTot OBJECT-TYPE
    SYNTAX      Unsigned32
    MAX-ACCESS  read-only
    STATUS      current
    DESCRIPTION
        "Near end total frame loss ratio in per mille (average since last
         clear)."
    ::= { gamMepStatusLmEntry 12 }

gamMepStatusLmFarEndLosRatioTot OBJECT-TYPE
    SYNTAX      Unsigned32
    MAX-ACCESS  read-only
    STATUS      current
    DESCRIPTION
        "Far end total frame loss ratio in per mille (average since last clear)."
    ::= { gamMepStatusLmEntry 13 }

gamMepStatusLmNearEndLosRatioMin OBJECT-TYPE
    SYNTAX      Unsigned32
    MAX-ACCESS  read-only
    STATUS      current
    DESCRIPTION
        "Near end minimum frame loss ratio in per mille (since last clear)."
    ::= { gamMepStatusLmEntry 14 }

gamMepStatusLmFarEndLosRatioMin OBJECT-TYPE
    SYNTAX      Unsigned32
    MAX-ACCESS  read-only
    STATUS      current
    DESCRIPTION
        "Far end minimum frame loss ratio in per mille (since last clear)."
    ::= { gamMepStatusLmEntry 15 }

gamMepStatusLmNearEndLosRatioMax OBJECT-TYPE
    SYNTAX      Unsigned32
    MAX-ACCESS  read-only
    STATUS      current
    DESCRIPTION
        "Near end maximum frame loss ratio in per mille (since last clear)."
    ::= { gamMepStatusLmEntry 16 }

gamMepStatusLmFarEndLosRatioMax OBJECT-TYPE
    SYNTAX      Unsigned32
    MAX-ACCESS  read-only
    STATUS      current
    DESCRIPTION
        "Far end maximum frame loss ratio in per mille (since last clear)."
    ::= { gamMepStatusLmEntry 17 }

gamMepStatusLmElapsedIntervals OBJECT-TYPE
    SYNTAX      Unsigned32
    MAX-ACCESS  read-only
    STATUS      current
    DESCRIPTION
        "The number of expired frame loss ratio measurement intervals."
    ::= { gamMepStatusLmEntry 18 }

gamMepStatusLmPeerTable OBJECT-TYPE
    SYNTAX      SEQUENCE OF GAMMepStatusLmPeerEntry
    MAX-ACCESS  not-accessible
    STATUS      current
    DESCRIPTION
        "This is a table of Loss Measurement peer status"
    ::= { gamMepStatusLm 2 }

gamMepStatusLmPeerEntry OBJECT-TYPE
    SYNTAX      GAMMepStatusLmPeerEntry
    MAX-ACCESS  not-accessible
    STATUS      current
    DESCRIPTION
        "This is a Loss Measurement peer status"
    INDEX       { gamMepStatusLmPeerId, gamMepStatusLmPeerPeerId }
    ::= { gamMepStatusLmPeerTable 1 }

GAMMepStatusLmPeerEntry ::= SEQUENCE {
    gamMepStatusLmPeerId                    Integer32,
    gamMepStatusLmPeerPeerId                Integer32,
    gamMepStatusLmPeerTxCounter             Unsigned32,
    gamMepStatusLmPeerRxCounter             Unsigned32,
    gamMepStatusLmPeerNearEndLosCounterTot  Integer32,
    gamMepStatusLmPeerFarEndLosCounterTot   Integer32,
    gamMepStatusLmPeerNearEndLosRatioInt    Unsigned32,
    gamMepStatusLmPeerFarEndLosRatioInt     Unsigned32,
    gamMepStatusLmPeerNearEndLosCounterInt  Unsigned32,
    gamMepStatusLmPeerFarEndLosCounterInt   Unsigned32,
    gamMepStatusLmPeerNearEndLosThCnt       Unsigned32,
    gamMepStatusLmPeerFarEndLosThCnt        Unsigned32,
    gamMepStatusLmPeerNearEndLosRatioTot    Unsigned32,
    gamMepStatusLmPeerFarEndLosRatioTot     Unsigned32,
    gamMepStatusLmPeerNearEndLosRatioMin    Unsigned32,
    gamMepStatusLmPeerFarEndLosRatioMin     Unsigned32,
    gamMepStatusLmPeerNearEndLosRatioMax    Unsigned32,
    gamMepStatusLmPeerFarEndLosRatioMax     Unsigned32,
    gamMepStatusLmPeerElapsedIntervals      Unsigned32
}

gamMepStatusLmPeerId OBJECT-TYPE
    SYNTAX      Integer32 (1..2147483647)
    MAX-ACCESS  accessible-for-notify
    STATUS      current
    DESCRIPTION
        "The MEP instance ID"
    ::= { gamMepStatusLmPeerEntry 1 }

gamMepStatusLmPeerPeerId OBJECT-TYPE
    SYNTAX      Integer32 (0..2147483647)
    MAX-ACCESS  accessible-for-notify
    STATUS      current
    DESCRIPTION
        "The Peer MEP ID"
    ::= { gamMepStatusLmPeerEntry 2 }

gamMepStatusLmPeerTxCounter OBJECT-TYPE
    SYNTAX      Unsigned32
    MAX-ACCESS  read-only
    STATUS      current
    DESCRIPTION
        "Transmitted PDU (LMM - CCM) containing counters."
    ::= { gamMepStatusLmPeerEntry 3 }

gamMepStatusLmPeerRxCounter OBJECT-TYPE
    SYNTAX      Unsigned32
    MAX-ACCESS  read-only
    STATUS      current
    DESCRIPTION
        "Received PDU (LMM - CCM) containing counters."
    ::= { gamMepStatusLmPeerEntry 4 }

gamMepStatusLmPeerNearEndLosCounterTot OBJECT-TYPE
    SYNTAX      Integer32
    MAX-ACCESS  read-only
    STATUS      current
    DESCRIPTION
        "Near end total frame loss counter."
    ::= { gamMepStatusLmPeerEntry 5 }

gamMepStatusLmPeerFarEndLosCounterTot OBJECT-TYPE
    SYNTAX      Integer32
    MAX-ACCESS  read-only
    STATUS      current
    DESCRIPTION
        "Far end total frame loss counter."
    ::= { gamMepStatusLmPeerEntry 6 }

gamMepStatusLmPeerNearEndLosRatioInt OBJECT-TYPE
    SYNTAX      Unsigned32
    MAX-ACCESS  read-only
    STATUS      current
    DESCRIPTION
        "Near end frame loss ratio for interval in per mille."
    ::= { gamMepStatusLmPeerEntry 7 }

gamMepStatusLmPeerFarEndLosRatioInt OBJECT-TYPE
    SYNTAX      Unsigned32
    MAX-ACCESS  read-only
    STATUS      current
    DESCRIPTION
        "Far end frame loss ratio for interval in per mille."
    ::= { gamMepStatusLmPeerEntry 8 }

gamMepStatusLmPeerNearEndLosCounterInt OBJECT-TYPE
    SYNTAX      Unsigned32
    MAX-ACCESS  read-only
    STATUS      current
    DESCRIPTION
        "Number of measurements that has contributed to near end loss (since
         last clear)."
    ::= { gamMepStatusLmPeerEntry 9 }

gamMepStatusLmPeerFarEndLosCounterInt OBJECT-TYPE
    SYNTAX      Unsigned32
    MAX-ACCESS  read-only
    STATUS      current
    DESCRIPTION
        "Number of measurements that has contributed to far end loss (since last
         clear)."
    ::= { gamMepStatusLmPeerEntry 10 }

gamMepStatusLmPeerNearEndLosThCnt OBJECT-TYPE
    SYNTAX      Unsigned32
    MAX-ACCESS  read-only
    STATUS      current
    DESCRIPTION
        "Near end frame loss threshold count."
    ::= { gamMepStatusLmPeerEntry 11 }

gamMepStatusLmPeerFarEndLosThCnt OBJECT-TYPE
    SYNTAX      Unsigned32
    MAX-ACCESS  read-only
    STATUS      current
    DESCRIPTION
        "Far end frame loss threshold count."
    ::= { gamMepStatusLmPeerEntry 12 }

gamMepStatusLmPeerNearEndLosRatioTot OBJECT-TYPE
    SYNTAX      Unsigned32
    MAX-ACCESS  read-only
    STATUS      current
    DESCRIPTION
        "Near end total frame loss ratio in per mille (average since last
         clear)."
    ::= { gamMepStatusLmPeerEntry 13 }

gamMepStatusLmPeerFarEndLosRatioTot OBJECT-TYPE
    SYNTAX      Unsigned32
    MAX-ACCESS  read-only
    STATUS      current
    DESCRIPTION
        "Far end total frame loss ratio in per mille (average since last clear)."
    ::= { gamMepStatusLmPeerEntry 14 }

gamMepStatusLmPeerNearEndLosRatioMin OBJECT-TYPE
    SYNTAX      Unsigned32
    MAX-ACCESS  read-only
    STATUS      current
    DESCRIPTION
        "Near end minimum frame loss ratio in per mille (since last clear)."
    ::= { gamMepStatusLmPeerEntry 15 }

gamMepStatusLmPeerFarEndLosRatioMin OBJECT-TYPE
    SYNTAX      Unsigned32
    MAX-ACCESS  read-only
    STATUS      current
    DESCRIPTION
        "Far end minimum frame loss ratio in per mille (since last clear)."
    ::= { gamMepStatusLmPeerEntry 16 }

gamMepStatusLmPeerNearEndLosRatioMax OBJECT-TYPE
    SYNTAX      Unsigned32
    MAX-ACCESS  read-only
    STATUS      current
    DESCRIPTION
        "Near end maximum frame loss ratio in per mille (since last clear)."
    ::= { gamMepStatusLmPeerEntry 17 }

gamMepStatusLmPeerFarEndLosRatioMax OBJECT-TYPE
    SYNTAX      Unsigned32
    MAX-ACCESS  read-only
    STATUS      current
    DESCRIPTION
        "Far end maximum frame loss ratio in per mille (since last clear)."
    ::= { gamMepStatusLmPeerEntry 18 }

gamMepStatusLmPeerElapsedIntervals OBJECT-TYPE
    SYNTAX      Unsigned32
    MAX-ACCESS  read-only
    STATUS      current
    DESCRIPTION
        "The number of expired frame loss ratio measurement intervals."
    ::= { gamMepStatusLmPeerEntry 19 }

gamMepStatusDm OBJECT IDENTIFIER
    ::= { gamMepStatus 3 }

gamMepStatusDmTwoWayTable OBJECT-TYPE
    SYNTAX      SEQUENCE OF GAMMepStatusDmTwoWayEntry
    MAX-ACCESS  not-accessible
    STATUS      current
    DESCRIPTION
        "This is a table of Delay Measurement Two Way status"
    ::= { gamMepStatusDm 1 }

gamMepStatusDmTwoWayEntry OBJECT-TYPE
    SYNTAX      GAMMepStatusDmTwoWayEntry
    MAX-ACCESS  not-accessible
    STATUS      current
    DESCRIPTION
        "This is a Delay Measurement Two Way status"
    INDEX       { gamMepStatusDmTwoWayId }
    ::= { gamMepStatusDmTwoWayTable 1 }

GAMMepStatusDmTwoWayEntry ::= SEQUENCE {
    gamMepStatusDmTwoWayId                          Integer32,
    gamMepStatusDmTwoWayTxCounter                   Unsigned32,
    gamMepStatusDmTwoWayRxCounter                   Unsigned32,
    gamMepStatusDmTwoWayRxTimeOutCounter            Unsigned32,
    gamMepStatusDmTwoWayRxErrorCounter              Unsigned32,
    gamMepStatusDmTwoWayInternalOverflowCounter     Unsigned32,
    gamMepStatusDmTwoWayAverageDelay                Unsigned32,
    gamMepStatusDmTwoWayAverageLastnDelay           Unsigned32,
    gamMepStatusDmTwoWayAverageDelayVariation       Unsigned32,
    gamMepStatusDmTwoWayAverageLastnDelayVariation  Unsigned32,
    gamMepStatusDmTwoWayMinimumDelay                Unsigned32,
    gamMepStatusDmTwoWayMaximumDelay                Unsigned32,
    gamMepStatusDmTwoWayMinimumDelayVariation       Unsigned32,
    gamMepStatusDmTwoWayMaximumDelayVariation       Unsigned32,
    gamMepStatusDmTwoWayTimeUnit                    GAMMepDmTimeUnit
}

gamMepStatusDmTwoWayId OBJECT-TYPE
    SYNTAX      Integer32 (1..2147483647)
    MAX-ACCESS  accessible-for-notify
    STATUS      current
    DESCRIPTION
        "The MEP instance ID"
    ::= { gamMepStatusDmTwoWayEntry 1 }

gamMepStatusDmTwoWayTxCounter OBJECT-TYPE
    SYNTAX      Unsigned32
    MAX-ACCESS  read-only
    STATUS      current
    DESCRIPTION
        "Transmitted DMM/1DM frames."
    ::= { gamMepStatusDmTwoWayEntry 2 }

gamMepStatusDmTwoWayRxCounter OBJECT-TYPE
    SYNTAX      Unsigned32
    MAX-ACCESS  read-only
    STATUS      current
    DESCRIPTION
        "Received DMM/1DM frames."
    ::= { gamMepStatusDmTwoWayEntry 3 }

gamMepStatusDmTwoWayRxTimeOutCounter OBJECT-TYPE
    SYNTAX      Unsigned32
    MAX-ACCESS  read-only
    STATUS      current
    DESCRIPTION
        "Received DMR time-out. After transmission of DMM, the DMR is expected
         to be received within 1 sec."
    ::= { gamMepStatusDmTwoWayEntry 4 }

gamMepStatusDmTwoWayRxErrorCounter OBJECT-TYPE
    SYNTAX      Unsigned32
    MAX-ACCESS  read-only
    STATUS      current
    DESCRIPTION
        "Received error counter. It is considered an error if a delay is
         negative or above 1 sec."
    ::= { gamMepStatusDmTwoWayEntry 5 }

gamMepStatusDmTwoWayInternalOverflowCounter OBJECT-TYPE
    SYNTAX      Unsigned32
    MAX-ACCESS  read-only
    STATUS      current
    DESCRIPTION
        "The internal total delay counter overflow counter."
    ::= { gamMepStatusDmTwoWayEntry 6 }

gamMepStatusDmTwoWayAverageDelay OBJECT-TYPE
    SYNTAX      Unsigned32
    MAX-ACCESS  read-only
    STATUS      current
    DESCRIPTION
        "The total average delay."
    ::= { gamMepStatusDmTwoWayEntry 7 }

gamMepStatusDmTwoWayAverageLastnDelay OBJECT-TYPE
    SYNTAX      Unsigned32
    MAX-ACCESS  read-only
    STATUS      current
    DESCRIPTION
        "The last N average delay."
    ::= { gamMepStatusDmTwoWayEntry 8 }

gamMepStatusDmTwoWayAverageDelayVariation OBJECT-TYPE
    SYNTAX      Unsigned32
    MAX-ACCESS  read-only
    STATUS      current
    DESCRIPTION
        "The total average delay variation."
    ::= { gamMepStatusDmTwoWayEntry 9 }

gamMepStatusDmTwoWayAverageLastnDelayVariation OBJECT-TYPE
    SYNTAX      Unsigned32
    MAX-ACCESS  read-only
    STATUS      current
    DESCRIPTION
        "The last N average delay variation."
    ::= { gamMepStatusDmTwoWayEntry 10 }

gamMepStatusDmTwoWayMinimumDelay OBJECT-TYPE
    SYNTAX      Unsigned32
    MAX-ACCESS  read-only
    STATUS      current
    DESCRIPTION
        "The minimum delay measured."
    ::= { gamMepStatusDmTwoWayEntry 11 }

gamMepStatusDmTwoWayMaximumDelay OBJECT-TYPE
    SYNTAX      Unsigned32
    MAX-ACCESS  read-only
    STATUS      current
    DESCRIPTION
        "The maximum delay measured."
    ::= { gamMepStatusDmTwoWayEntry 12 }

gamMepStatusDmTwoWayMinimumDelayVariation OBJECT-TYPE
    SYNTAX      Unsigned32
    MAX-ACCESS  read-only
    STATUS      current
    DESCRIPTION
        "The minimum delay variation measured."
    ::= { gamMepStatusDmTwoWayEntry 13 }

gamMepStatusDmTwoWayMaximumDelayVariation OBJECT-TYPE
    SYNTAX      Unsigned32
    MAX-ACCESS  read-only
    STATUS      current
    DESCRIPTION
        "The maximum delay variation measured."
    ::= { gamMepStatusDmTwoWayEntry 14 }

gamMepStatusDmTwoWayTimeUnit OBJECT-TYPE
    SYNTAX      GAMMepDmTimeUnit
    MAX-ACCESS  read-only
    STATUS      current
    DESCRIPTION
        "Calculation time unit."
    ::= { gamMepStatusDmTwoWayEntry 15 }

gamMepStatusDmOneWayFarNearTable OBJECT-TYPE
    SYNTAX      SEQUENCE OF GAMMepStatusDmOneWayFarNearEntry
    MAX-ACCESS  not-accessible
    STATUS      current
    DESCRIPTION
        "This is a table of Delay Measurement One Way Far to Near status"
    ::= { gamMepStatusDm 2 }

gamMepStatusDmOneWayFarNearEntry OBJECT-TYPE
    SYNTAX      GAMMepStatusDmOneWayFarNearEntry
    MAX-ACCESS  not-accessible
    STATUS      current
    DESCRIPTION
        "This is a Delay Measurement Two Way Far to Near status"
    INDEX       { gamMepStatusDmOneWayFarNearId }
    ::= { gamMepStatusDmOneWayFarNearTable 1 }

GAMMepStatusDmOneWayFarNearEntry ::= SEQUENCE {
    gamMepStatusDmOneWayFarNearId                          Integer32,
    gamMepStatusDmOneWayFarNearTxCounter                   Unsigned32,
    gamMepStatusDmOneWayFarNearRxCounter                   Unsigned32,
    gamMepStatusDmOneWayFarNearRxTimeOutCounter            Unsigned32,
    gamMepStatusDmOneWayFarNearRxErrorCounter              Unsigned32,
    gamMepStatusDmOneWayFarNearInternalOverflowCounter     Unsigned32,
    gamMepStatusDmOneWayFarNearAverageDelay                Unsigned32,
    gamMepStatusDmOneWayFarNearAverageLastnDelay           Unsigned32,
    gamMepStatusDmOneWayFarNearAverageDelayVariation       Unsigned32,
    gamMepStatusDmOneWayFarNearAverageLastnDelayVariation  Unsigned32,
    gamMepStatusDmOneWayFarNearMinimumDelay                Unsigned32,
    gamMepStatusDmOneWayFarNearMaximumDelay                Unsigned32,
    gamMepStatusDmOneWayFarNearMinimumDelayVariation       Unsigned32,
    gamMepStatusDmOneWayFarNearMaximumDelayVariation       Unsigned32,
    gamMepStatusDmOneWayFarNearTimeUnit                    GAMMepDmTimeUnit
}

gamMepStatusDmOneWayFarNearId OBJECT-TYPE
    SYNTAX      Integer32 (1..2147483647)
    MAX-ACCESS  accessible-for-notify
    STATUS      current
    DESCRIPTION
        "The MEP instance ID"
    ::= { gamMepStatusDmOneWayFarNearEntry 1 }

gamMepStatusDmOneWayFarNearTxCounter OBJECT-TYPE
    SYNTAX      Unsigned32
    MAX-ACCESS  read-only
    STATUS      current
    DESCRIPTION
        "Transmitted DMM/1DM frames."
    ::= { gamMepStatusDmOneWayFarNearEntry 2 }

gamMepStatusDmOneWayFarNearRxCounter OBJECT-TYPE
    SYNTAX      Unsigned32
    MAX-ACCESS  read-only
    STATUS      current
    DESCRIPTION
        "Received DMM/1DM frames."
    ::= { gamMepStatusDmOneWayFarNearEntry 3 }

gamMepStatusDmOneWayFarNearRxTimeOutCounter OBJECT-TYPE
    SYNTAX      Unsigned32
    MAX-ACCESS  read-only
    STATUS      current
    DESCRIPTION
        "Received DMR time-out. After transmission of DMM, the DMR is expected
         to be received within 1 sec."
    ::= { gamMepStatusDmOneWayFarNearEntry 4 }

gamMepStatusDmOneWayFarNearRxErrorCounter OBJECT-TYPE
    SYNTAX      Unsigned32
    MAX-ACCESS  read-only
    STATUS      current
    DESCRIPTION
        "Received error counter. It is considered an error if a delay is
         negative or above 1 sec."
    ::= { gamMepStatusDmOneWayFarNearEntry 5 }

gamMepStatusDmOneWayFarNearInternalOverflowCounter OBJECT-TYPE
    SYNTAX      Unsigned32
    MAX-ACCESS  read-only
    STATUS      current
    DESCRIPTION
        "The internal total delay counter overflow counter."
    ::= { gamMepStatusDmOneWayFarNearEntry 6 }

gamMepStatusDmOneWayFarNearAverageDelay OBJECT-TYPE
    SYNTAX      Unsigned32
    MAX-ACCESS  read-only
    STATUS      current
    DESCRIPTION
        "The total average delay."
    ::= { gamMepStatusDmOneWayFarNearEntry 7 }

gamMepStatusDmOneWayFarNearAverageLastnDelay OBJECT-TYPE
    SYNTAX      Unsigned32
    MAX-ACCESS  read-only
    STATUS      current
    DESCRIPTION
        "The last N average delay."
    ::= { gamMepStatusDmOneWayFarNearEntry 8 }

gamMepStatusDmOneWayFarNearAverageDelayVariation OBJECT-TYPE
    SYNTAX      Unsigned32
    MAX-ACCESS  read-only
    STATUS      current
    DESCRIPTION
        "The total average delay variation."
    ::= { gamMepStatusDmOneWayFarNearEntry 9 }

gamMepStatusDmOneWayFarNearAverageLastnDelayVariation OBJECT-TYPE
    SYNTAX      Unsigned32
    MAX-ACCESS  read-only
    STATUS      current
    DESCRIPTION
        "The last N average delay variation."
    ::= { gamMepStatusDmOneWayFarNearEntry 10 }

gamMepStatusDmOneWayFarNearMinimumDelay OBJECT-TYPE
    SYNTAX      Unsigned32
    MAX-ACCESS  read-only
    STATUS      current
    DESCRIPTION
        "The minimum delay measured."
    ::= { gamMepStatusDmOneWayFarNearEntry 11 }

gamMepStatusDmOneWayFarNearMaximumDelay OBJECT-TYPE
    SYNTAX      Unsigned32
    MAX-ACCESS  read-only
    STATUS      current
    DESCRIPTION
        "The maximum delay measured."
    ::= { gamMepStatusDmOneWayFarNearEntry 12 }

gamMepStatusDmOneWayFarNearMinimumDelayVariation OBJECT-TYPE
    SYNTAX      Unsigned32
    MAX-ACCESS  read-only
    STATUS      current
    DESCRIPTION
        "The minimum delay variation measured."
    ::= { gamMepStatusDmOneWayFarNearEntry 13 }

gamMepStatusDmOneWayFarNearMaximumDelayVariation OBJECT-TYPE
    SYNTAX      Unsigned32
    MAX-ACCESS  read-only
    STATUS      current
    DESCRIPTION
        "The maximum delay variation measured."
    ::= { gamMepStatusDmOneWayFarNearEntry 14 }

gamMepStatusDmOneWayFarNearTimeUnit OBJECT-TYPE
    SYNTAX      GAMMepDmTimeUnit
    MAX-ACCESS  read-only
    STATUS      current
    DESCRIPTION
        "Calculation time unit."
    ::= { gamMepStatusDmOneWayFarNearEntry 15 }

gamMepStatusDmOneWayNearFarTable OBJECT-TYPE
    SYNTAX      SEQUENCE OF GAMMepStatusDmOneWayNearFarEntry
    MAX-ACCESS  not-accessible
    STATUS      current
    DESCRIPTION
        "This is a table of Delay Measurement One Way Near to Far status"
    ::= { gamMepStatusDm 3 }

gamMepStatusDmOneWayNearFarEntry OBJECT-TYPE
    SYNTAX      GAMMepStatusDmOneWayNearFarEntry
    MAX-ACCESS  not-accessible
    STATUS      current
    DESCRIPTION
        "This is a Delay Measurement Two Way Near to Far status"
    INDEX       { gamMepStatusDmOneWayNearFarId }
    ::= { gamMepStatusDmOneWayNearFarTable 1 }

GAMMepStatusDmOneWayNearFarEntry ::= SEQUENCE {
    gamMepStatusDmOneWayNearFarId                          Integer32,
    gamMepStatusDmOneWayNearFarTxCounter                   Unsigned32,
    gamMepStatusDmOneWayNearFarRxCounter                   Unsigned32,
    gamMepStatusDmOneWayNearFarRxTimeOutCounter            Unsigned32,
    gamMepStatusDmOneWayNearFarRxErrorCounter              Unsigned32,
    gamMepStatusDmOneWayNearFarInternalOverflowCounter     Unsigned32,
    gamMepStatusDmOneWayNearFarAverageDelay                Unsigned32,
    gamMepStatusDmOneWayNearFarAverageLastnDelay           Unsigned32,
    gamMepStatusDmOneWayNearFarAverageDelayVariation       Unsigned32,
    gamMepStatusDmOneWayNearFarAverageLastnDelayVariation  Unsigned32,
    gamMepStatusDmOneWayNearFarMinimumDelay                Unsigned32,
    gamMepStatusDmOneWayNearFarMaximumDelay                Unsigned32,
    gamMepStatusDmOneWayNearFarMinimumDelayVariation       Unsigned32,
    gamMepStatusDmOneWayNearFarMaximumDelayVariation       Unsigned32,
    gamMepStatusDmOneWayNearFarTimeUnit                    GAMMepDmTimeUnit
}

gamMepStatusDmOneWayNearFarId OBJECT-TYPE
    SYNTAX      Integer32 (1..2147483647)
    MAX-ACCESS  accessible-for-notify
    STATUS      current
    DESCRIPTION
        "The MEP instance ID"
    ::= { gamMepStatusDmOneWayNearFarEntry 1 }

gamMepStatusDmOneWayNearFarTxCounter OBJECT-TYPE
    SYNTAX      Unsigned32
    MAX-ACCESS  read-only
    STATUS      current
    DESCRIPTION
        "Transmitted DMM/1DM frames."
    ::= { gamMepStatusDmOneWayNearFarEntry 2 }

gamMepStatusDmOneWayNearFarRxCounter OBJECT-TYPE
    SYNTAX      Unsigned32
    MAX-ACCESS  read-only
    STATUS      current
    DESCRIPTION
        "Received DMM/1DM frames."
    ::= { gamMepStatusDmOneWayNearFarEntry 3 }

gamMepStatusDmOneWayNearFarRxTimeOutCounter OBJECT-TYPE
    SYNTAX      Unsigned32
    MAX-ACCESS  read-only
    STATUS      current
    DESCRIPTION
        "Received DMR time-out. After transmission of DMM, the DMR is expected
         to be received within 1 sec."
    ::= { gamMepStatusDmOneWayNearFarEntry 4 }

gamMepStatusDmOneWayNearFarRxErrorCounter OBJECT-TYPE
    SYNTAX      Unsigned32
    MAX-ACCESS  read-only
    STATUS      current
    DESCRIPTION
        "Received error counter. It is considered an error if a delay is
         negative or above 1 sec."
    ::= { gamMepStatusDmOneWayNearFarEntry 5 }

gamMepStatusDmOneWayNearFarInternalOverflowCounter OBJECT-TYPE
    SYNTAX      Unsigned32
    MAX-ACCESS  read-only
    STATUS      current
    DESCRIPTION
        "The internal total delay counter overflow counter."
    ::= { gamMepStatusDmOneWayNearFarEntry 6 }

gamMepStatusDmOneWayNearFarAverageDelay OBJECT-TYPE
    SYNTAX      Unsigned32
    MAX-ACCESS  read-only
    STATUS      current
    DESCRIPTION
        "The total average delay."
    ::= { gamMepStatusDmOneWayNearFarEntry 7 }

gamMepStatusDmOneWayNearFarAverageLastnDelay OBJECT-TYPE
    SYNTAX      Unsigned32
    MAX-ACCESS  read-only
    STATUS      current
    DESCRIPTION
        "The last N average delay."
    ::= { gamMepStatusDmOneWayNearFarEntry 8 }

gamMepStatusDmOneWayNearFarAverageDelayVariation OBJECT-TYPE
    SYNTAX      Unsigned32
    MAX-ACCESS  read-only
    STATUS      current
    DESCRIPTION
        "The total average delay variation."
    ::= { gamMepStatusDmOneWayNearFarEntry 9 }

gamMepStatusDmOneWayNearFarAverageLastnDelayVariation OBJECT-TYPE
    SYNTAX      Unsigned32
    MAX-ACCESS  read-only
    STATUS      current
    DESCRIPTION
        "The last N average delay variation."
    ::= { gamMepStatusDmOneWayNearFarEntry 10 }

gamMepStatusDmOneWayNearFarMinimumDelay OBJECT-TYPE
    SYNTAX      Unsigned32
    MAX-ACCESS  read-only
    STATUS      current
    DESCRIPTION
        "The minimum delay measured."
    ::= { gamMepStatusDmOneWayNearFarEntry 11 }

gamMepStatusDmOneWayNearFarMaximumDelay OBJECT-TYPE
    SYNTAX      Unsigned32
    MAX-ACCESS  read-only
    STATUS      current
    DESCRIPTION
        "The maximum delay measured."
    ::= { gamMepStatusDmOneWayNearFarEntry 12 }

gamMepStatusDmOneWayNearFarMinimumDelayVariation OBJECT-TYPE
    SYNTAX      Unsigned32
    MAX-ACCESS  read-only
    STATUS      current
    DESCRIPTION
        "The minimum delay variation measured."
    ::= { gamMepStatusDmOneWayNearFarEntry 13 }

gamMepStatusDmOneWayNearFarMaximumDelayVariation OBJECT-TYPE
    SYNTAX      Unsigned32
    MAX-ACCESS  read-only
    STATUS      current
    DESCRIPTION
        "The maximum delay variation measured."
    ::= { gamMepStatusDmOneWayNearFarEntry 14 }

gamMepStatusDmOneWayNearFarTimeUnit OBJECT-TYPE
    SYNTAX      GAMMepDmTimeUnit
    MAX-ACCESS  read-only
    STATUS      current
    DESCRIPTION
        "Calculation time unit."
    ::= { gamMepStatusDmOneWayNearFarEntry 15 }

gamMepStatusLb OBJECT IDENTIFIER
    ::= { gamMepStatus 4 }

gamMepStatusLbTable OBJECT-TYPE
    SYNTAX      SEQUENCE OF GAMMepStatusLbEntry
    MAX-ACCESS  not-accessible
    STATUS      current
    DESCRIPTION
        "This is a table of Loop Back status"
    ::= { gamMepStatusLb 1 }

gamMepStatusLbEntry OBJECT-TYPE
    SYNTAX      GAMMepStatusLbEntry
    MAX-ACCESS  not-accessible
    STATUS      current
    DESCRIPTION
        "This is a Loop Back status"
    INDEX       { gamMepStatusLbId }
    ::= { gamMepStatusLbTable 1 }

GAMMepStatusLbEntry ::= SEQUENCE {
    gamMepStatusLbId              Integer32,
    gamMepStatusLbTransactionId   Unsigned32,
    gamMepStatusLbReplyCounter    Unsigned32,
    gamMepStatusLbLbmTransmitted  Counter64
}

gamMepStatusLbId OBJECT-TYPE
    SYNTAX      Integer32 (1..2147483647)
    MAX-ACCESS  accessible-for-notify
    STATUS      current
    DESCRIPTION
        "The MEP instance ID"
    ::= { gamMepStatusLbEntry 1 }

gamMepStatusLbTransactionId OBJECT-TYPE
    SYNTAX      Unsigned32
    MAX-ACCESS  read-only
    STATUS      current
    DESCRIPTION
        "This is the transaction id that is used to send the next LBM."
    ::= { gamMepStatusLbEntry 2 }

gamMepStatusLbReplyCounter OBJECT-TYPE
    SYNTAX      Unsigned32
    MAX-ACCESS  read-only
    STATUS      current
    DESCRIPTION
        "The number of replying MAC. In case of 'infinite' LBM there is only one
         reply."
    ::= { gamMepStatusLbEntry 3 }

gamMepStatusLbLbmTransmitted OBJECT-TYPE
    SYNTAX      Counter64
    MAX-ACCESS  read-only
    STATUS      current
    DESCRIPTION
        "The number of transmitted LBM."
    ::= { gamMepStatusLbEntry 4 }

gamMepStatusLbReplyTable OBJECT-TYPE
    SYNTAX      SEQUENCE OF GAMMepStatusLbReplyEntry
    MAX-ACCESS  not-accessible
    STATUS      current
    DESCRIPTION
        "This is a table of Loop Back reply status"
    ::= { gamMepStatusLb 2 }

gamMepStatusLbReplyEntry OBJECT-TYPE
    SYNTAX      GAMMepStatusLbReplyEntry
    MAX-ACCESS  not-accessible
    STATUS      current
    DESCRIPTION
        "This is a Loop Back reply status"
    INDEX       { gamMepStatusLbReplyId, gamMepStatusLbReplyReplyId }
    ::= { gamMepStatusLbReplyTable 1 }

GAMMepStatusLbReplyEntry ::= SEQUENCE {
    gamMepStatusLbReplyId           Integer32,
    gamMepStatusLbReplyReplyId      Integer32,
    gamMepStatusLbReplyMac          MacAddress,
    gamMepStatusLbReplyLbrReceived  Counter64,
    gamMepStatusLbReplyOutOfOrder   Counter64,
    gamMepStatusLbReplyMepMipId     OCTET STRING
}

gamMepStatusLbReplyId OBJECT-TYPE
    SYNTAX      Integer32 (1..2147483647)
    MAX-ACCESS  accessible-for-notify
    STATUS      current
    DESCRIPTION
        "The MEP instance ID"
    ::= { gamMepStatusLbReplyEntry 1 }

gamMepStatusLbReplyReplyId OBJECT-TYPE
    SYNTAX      Integer32 (0..2147483647)
    MAX-ACCESS  accessible-for-notify
    STATUS      current
    DESCRIPTION
        "The LB or LT Reply id"
    ::= { gamMepStatusLbReplyEntry 2 }

gamMepStatusLbReplyMac OBJECT-TYPE
    SYNTAX      MacAddress
    MAX-ACCESS  read-only
    STATUS      current
    DESCRIPTION
        "LBR source MAC - this is only relevant if not 'infinite' LBM and not
         MPLS loopback"
    ::= { gamMepStatusLbReplyEntry 3 }

gamMepStatusLbReplyLbrReceived OBJECT-TYPE
    SYNTAX      Counter64
    MAX-ACCESS  read-only
    STATUS      current
    DESCRIPTION
        "Number LBR received from MAC."
    ::= { gamMepStatusLbReplyEntry 4 }

gamMepStatusLbReplyOutOfOrder OBJECT-TYPE
    SYNTAX      Counter64
    MAX-ACCESS  read-only
    STATUS      current
    DESCRIPTION
        "The OOO counter."
    ::= { gamMepStatusLbReplyEntry 5 }

gamMepStatusLbReplyMepMipId OBJECT-TYPE
    SYNTAX      OCTET STRING (SIZE(16))
    MAX-ACCESS  read-only
    STATUS      current
    DESCRIPTION
        "Replying MEP/MIP ID - only relevant for loopback on MPLS"
    ::= { gamMepStatusLbReplyEntry 6 }

gamMepStatusTst OBJECT IDENTIFIER
    ::= { gamMepStatus 5 }

gamMepStatusTstTable OBJECT-TYPE
    SYNTAX      SEQUENCE OF GAMMepStatusTstEntry
    MAX-ACCESS  not-accessible
    STATUS      current
    DESCRIPTION
        "This is a table of Test Signal status"
    ::= { gamMepStatusTst 1 }

gamMepStatusTstEntry OBJECT-TYPE
    SYNTAX      GAMMepStatusTstEntry
    MAX-ACCESS  not-accessible
    STATUS      current
    DESCRIPTION
        "This is a Test Signal status"
    INDEX       { gamMepStatusTstId }
    ::= { gamMepStatusTstTable 1 }

GAMMepStatusTstEntry ::= SEQUENCE {
    gamMepStatusTstId                 Integer32,
    gamMepStatusTstTxCounter          Counter64,
    gamMepStatusTstRxCounter          Counter64,
    gamMepStatusTstOutOfOrderCounter  Counter64,
    gamMepStatusTstRxRate             Unsigned32,
    gamMepStatusTstTestTime           Unsigned32
}

gamMepStatusTstId OBJECT-TYPE
    SYNTAX      Integer32 (1..2147483647)
    MAX-ACCESS  accessible-for-notify
    STATUS      current
    DESCRIPTION
        "The MEP instance ID"
    ::= { gamMepStatusTstEntry 1 }

gamMepStatusTstTxCounter OBJECT-TYPE
    SYNTAX      Counter64
    MAX-ACCESS  read-only
    STATUS      current
    DESCRIPTION
        "Transmitted TST frames counter."
    ::= { gamMepStatusTstEntry 2 }

gamMepStatusTstRxCounter OBJECT-TYPE
    SYNTAX      Counter64
    MAX-ACCESS  read-only
    STATUS      current
    DESCRIPTION
        "REceived TST frames counter."
    ::= { gamMepStatusTstEntry 3 }

gamMepStatusTstOutOfOrderCounter OBJECT-TYPE
    SYNTAX      Counter64
    MAX-ACCESS  read-only
    STATUS      current
    DESCRIPTION
        "Out of Order counter."
    ::= { gamMepStatusTstEntry 4 }

gamMepStatusTstRxRate OBJECT-TYPE
    SYNTAX      Unsigned32
    MAX-ACCESS  read-only
    STATUS      current
    DESCRIPTION
        "Receive bit rate in Kbit/s."
    ::= { gamMepStatusTstEntry 5 }

gamMepStatusTstTestTime OBJECT-TYPE
    SYNTAX      Unsigned32
    MAX-ACCESS  read-only
    STATUS      current
    DESCRIPTION
        "Test time in seconds. The elapsed time since last clear."
    ::= { gamMepStatusTstEntry 6 }

gamMepStatusLt OBJECT IDENTIFIER
    ::= { gamMepStatus 6 }

gamMepStatusLtTable OBJECT-TYPE
    SYNTAX      SEQUENCE OF GAMMepStatusLtEntry
    MAX-ACCESS  not-accessible
    STATUS      current
    DESCRIPTION
        "This is a table of Link Trace status"
    ::= { gamMepStatusLt 1 }

gamMepStatusLtEntry OBJECT-TYPE
    SYNTAX      GAMMepStatusLtEntry
    MAX-ACCESS  not-accessible
    STATUS      current
    DESCRIPTION
        "This is a Link Trace status"
    INDEX       { gamMepStatusLtId }
    ::= { gamMepStatusLtTable 1 }

GAMMepStatusLtEntry ::= SEQUENCE {
    gamMepStatusLtId             Integer32,
    gamMepStatusLtTransactionId  Unsigned32,
    gamMepStatusLtReplyCount     Unsigned32
}

gamMepStatusLtId OBJECT-TYPE
    SYNTAX      Integer32 (1..2147483647)
    MAX-ACCESS  accessible-for-notify
    STATUS      current
    DESCRIPTION
        "The MEP instance ID"
    ::= { gamMepStatusLtEntry 1 }

gamMepStatusLtTransactionId OBJECT-TYPE
    SYNTAX      Unsigned32
    MAX-ACCESS  read-only
    STATUS      current
    DESCRIPTION
        "The transaction id of the latest Link Trace."
    ::= { gamMepStatusLtEntry 2 }

gamMepStatusLtReplyCount OBJECT-TYPE
    SYNTAX      Unsigned32
    MAX-ACCESS  read-only
    STATUS      current
    DESCRIPTION
        "Number of replies for this Link Trace transaction."
    ::= { gamMepStatusLtEntry 3 }

gamMepStatusLtReplyTable OBJECT-TYPE
    SYNTAX      SEQUENCE OF GAMMepStatusLtReplyEntry
    MAX-ACCESS  not-accessible
    STATUS      current
    DESCRIPTION
        "This is a table of Link Trace reply status"
    ::= { gamMepStatusLt 2 }

gamMepStatusLtReplyEntry OBJECT-TYPE
    SYNTAX      GAMMepStatusLtReplyEntry
    MAX-ACCESS  not-accessible
    STATUS      current
    DESCRIPTION
        "This is a Link Trace reply status"
    INDEX       { gamMepStatusLtReplyId, gamMepStatusLtReplyReplyId }
    ::= { gamMepStatusLtReplyTable 1 }

GAMMepStatusLtReplyEntry ::= SEQUENCE {
    gamMepStatusLtReplyId             Integer32,
    gamMepStatusLtReplyReplyId        Integer32,
    gamMepStatusLtReplyMode           GAMMepInstanceMode,
    gamMepStatusLtReplyDirection      GAMMepInstanceDirection,
    gamMepStatusLtReplyTtl            GAMUnsigned8,
    gamMepStatusLtReplyForwarded      TruthValue,
    gamMepStatusLtReplyRelayAction    GAMMepLtRelayAction,
    gamMepStatusLtReplyLastEgressMac  MacAddress,
    gamMepStatusLtReplyNextEgressMac  MacAddress
}

gamMepStatusLtReplyId OBJECT-TYPE
    SYNTAX      Integer32 (1..2147483647)
    MAX-ACCESS  accessible-for-notify
    STATUS      current
    DESCRIPTION
        "The MEP instance ID"
    ::= { gamMepStatusLtReplyEntry 1 }

gamMepStatusLtReplyReplyId OBJECT-TYPE
    SYNTAX      Integer32 (0..2147483647)
    MAX-ACCESS  accessible-for-notify
    STATUS      current
    DESCRIPTION
        "The LB or LT Reply id"
    ::= { gamMepStatusLtReplyEntry 2 }

gamMepStatusLtReplyMode OBJECT-TYPE
    SYNTAX      GAMMepInstanceMode
    MAX-ACCESS  read-only
    STATUS      current
    DESCRIPTION
        "The reply is done by a MEP or a MIP."
    ::= { gamMepStatusLtReplyEntry 3 }

gamMepStatusLtReplyDirection OBJECT-TYPE
    SYNTAX      GAMMepInstanceDirection
    MAX-ACCESS  read-only
    STATUS      current
    DESCRIPTION
        "The reply is done by a UP or a Down instance."
    ::= { gamMepStatusLtReplyEntry 4 }

gamMepStatusLtReplyTtl OBJECT-TYPE
    SYNTAX      GAMUnsigned8
    MAX-ACCESS  read-only
    STATUS      current
    DESCRIPTION
        "The reply TTL value."
    ::= { gamMepStatusLtReplyEntry 5 }

gamMepStatusLtReplyForwarded OBJECT-TYPE
    SYNTAX      TruthValue
    MAX-ACCESS  read-only
    STATUS      current
    DESCRIPTION
        "The LTM was forwarded."
    ::= { gamMepStatusLtReplyEntry 6 }

gamMepStatusLtReplyRelayAction OBJECT-TYPE
    SYNTAX      GAMMepLtRelayAction
    MAX-ACCESS  read-only
    STATUS      current
    DESCRIPTION
        "The relay action."
    ::= { gamMepStatusLtReplyEntry 7 }

gamMepStatusLtReplyLastEgressMac OBJECT-TYPE
    SYNTAX      MacAddress
    MAX-ACCESS  read-only
    STATUS      current
    DESCRIPTION
        "The Last Egress MAC for this reply."
    ::= { gamMepStatusLtReplyEntry 8 }

gamMepStatusLtReplyNextEgressMac OBJECT-TYPE
    SYNTAX      MacAddress
    MAX-ACCESS  read-only
    STATUS      current
    DESCRIPTION
        "The Next Egress MAC of this reply."
    ::= { gamMepStatusLtReplyEntry 9 }

gamMepStatusCc OBJECT IDENTIFIER
    ::= { gamMepStatus 7 }

gamMepStatusCcPeerTable OBJECT-TYPE
    SYNTAX      SEQUENCE OF GAMMepStatusCcPeerEntry
    MAX-ACCESS  not-accessible
    STATUS      current
    DESCRIPTION
        "This is a table of peer MEP CC status"
    ::= { gamMepStatusCc 2 }

gamMepStatusCcPeerEntry OBJECT-TYPE
    SYNTAX      GAMMepStatusCcPeerEntry
    MAX-ACCESS  not-accessible
    STATUS      current
    DESCRIPTION
        "This is a peer MEP CC status"
    INDEX       { gamMepStatusCcPeerId, gamMepStatusCcPeerPeerId }
    ::= { gamMepStatusCcPeerTable 1 }

GAMMepStatusCcPeerEntry ::= SEQUENCE {
    gamMepStatusCcPeerId              Integer32,
    gamMepStatusCcPeerPeerId          Integer32,
    gamMepStatusCcPeerOsTlvOuiFirst   GAMUnsigned8,
    gamMepStatusCcPeerOsTlvOuiSecond  GAMUnsigned8,
    gamMepStatusCcPeerOsTlvOuiThird   GAMUnsigned8,
    gamMepStatusCcPeerOsTlvSubType    GAMUnsigned8,
    gamMepStatusCcPeerOsTlvValue      GAMUnsigned8,
    gamMepStatusCcPeerIsTlvValue      GAMUnsigned8,
    gamMepStatusCcPeerPsTlvValue      GAMUnsigned8,
    gamMepStatusCcPeerOsTlvReceived   TruthValue,
    gamMepStatusCcPeerIsTlvReceived   TruthValue,
    gamMepStatusCcPeerPsTlvReceived   TruthValue
}

gamMepStatusCcPeerId OBJECT-TYPE
    SYNTAX      Integer32 (1..2147483647)
    MAX-ACCESS  accessible-for-notify
    STATUS      current
    DESCRIPTION
        "The MEP instance ID"
    ::= { gamMepStatusCcPeerEntry 1 }

gamMepStatusCcPeerPeerId OBJECT-TYPE
    SYNTAX      Integer32 (0..2147483647)
    MAX-ACCESS  accessible-for-notify
    STATUS      current
    DESCRIPTION
        "The Peer MEP ID"
    ::= { gamMepStatusCcPeerEntry 2 }

gamMepStatusCcPeerOsTlvOuiFirst OBJECT-TYPE
    SYNTAX      GAMUnsigned8
    MAX-ACCESS  read-only
    STATUS      current
    DESCRIPTION
        "Last received OS TLV - The OUI content first nibble"
    ::= { gamMepStatusCcPeerEntry 3 }

gamMepStatusCcPeerOsTlvOuiSecond OBJECT-TYPE
    SYNTAX      GAMUnsigned8
    MAX-ACCESS  read-only
    STATUS      current
    DESCRIPTION
        "Last received OS TLV - The OUI content second nibble"
    ::= { gamMepStatusCcPeerEntry 4 }

gamMepStatusCcPeerOsTlvOuiThird OBJECT-TYPE
    SYNTAX      GAMUnsigned8
    MAX-ACCESS  read-only
    STATUS      current
    DESCRIPTION
        "Last received OS TLV - The OUI content third nibble"
    ::= { gamMepStatusCcPeerEntry 5 }

gamMepStatusCcPeerOsTlvSubType OBJECT-TYPE
    SYNTAX      GAMUnsigned8
    MAX-ACCESS  read-only
    STATUS      current
    DESCRIPTION
        "Last received OS TLV - The Sub-Type content"
    ::= { gamMepStatusCcPeerEntry 6 }

gamMepStatusCcPeerOsTlvValue OBJECT-TYPE
    SYNTAX      GAMUnsigned8
    MAX-ACCESS  read-only
    STATUS      current
    DESCRIPTION
        "Last received OS TLV - The Value content"
    ::= { gamMepStatusCcPeerEntry 7 }

gamMepStatusCcPeerIsTlvValue OBJECT-TYPE
    SYNTAX      GAMUnsigned8
    MAX-ACCESS  read-only
    STATUS      current
    DESCRIPTION
        "Last received IS TLV - The Value content"
    ::= { gamMepStatusCcPeerEntry 8 }

gamMepStatusCcPeerPsTlvValue OBJECT-TYPE
    SYNTAX      GAMUnsigned8
    MAX-ACCESS  read-only
    STATUS      current
    DESCRIPTION
        "Last received PS TLV - The Value content"
    ::= { gamMepStatusCcPeerEntry 9 }

gamMepStatusCcPeerOsTlvReceived OBJECT-TYPE
    SYNTAX      TruthValue
    MAX-ACCESS  read-only
    STATUS      current
    DESCRIPTION
        "Last received CCM PDU contained OS TLV"
    ::= { gamMepStatusCcPeerEntry 10 }

gamMepStatusCcPeerIsTlvReceived OBJECT-TYPE
    SYNTAX      TruthValue
    MAX-ACCESS  read-only
    STATUS      current
    DESCRIPTION
        "Last received CCM PDU contained IS TLV"
    ::= { gamMepStatusCcPeerEntry 11 }

gamMepStatusCcPeerPsTlvReceived OBJECT-TYPE
    SYNTAX      TruthValue
    MAX-ACCESS  read-only
    STATUS      current
    DESCRIPTION
        "Last received CCM PDU contained PS TLV"
    ::= { gamMepStatusCcPeerEntry 12 }

gamMepStatusBfd OBJECT IDENTIFIER
    ::= { gamMepStatus 8 }

gamMepStatusBfdTable OBJECT-TYPE
    SYNTAX      SEQUENCE OF GAMMepStatusBfdEntry
    MAX-ACCESS  not-accessible
    STATUS      current
    DESCRIPTION
        "This is a table of MEP BFD status"
    ::= { gamMepStatusBfd 2 }

gamMepStatusBfdEntry OBJECT-TYPE
    SYNTAX      GAMMepStatusBfdEntry
    MAX-ACCESS  not-accessible
    STATUS      current
    DESCRIPTION
        "This is a MEP BFD status"
    INDEX       { gamMepStatusBfdId }
    ::= { gamMepStatusBfdTable 1 }

GAMMepStatusBfdEntry ::= SEQUENCE {
    gamMepStatusBfdId                  Integer32,
    gamMepStatusBfdCcTxCnt             GAMUnsigned64,
    gamMepStatusBfdValidCcRxCnt        GAMUnsigned64,
    gamMepStatusBfdInvalidCcRxCnt      GAMUnsigned64,
    gamMepStatusBfdCvTxCnt             GAMUnsigned64,
    gamMepStatusBfdValidCvRxCnt        GAMUnsigned64,
    gamMepStatusBfdInvalidCvRxCnt      GAMUnsigned64,
    gamMepStatusBfdMyDiscr             Unsigned32,
    gamMepStatusBfdSessionState0       GAMMepBfdSessionState,
    gamMepStatusBfdSessionState1       GAMMepBfdSessionState,
    gamMepStatusBfdLocalDiag           GAMMepBfdDiagnosticCode,
    gamMepStatusBfdRemoteSessionState  GAMMepBfdSessionState,
    gamMepStatusBfdRemoteDiag          GAMMepBfdDiagnosticCode,
    gamMepStatusBfdRemoteDiscr         Unsigned32,
    gamMepStatusBfdRemoteMinRx         Unsigned32,
    gamMepStatusBfdRemoteFlags         GAMUnsigned8,
    gamMepStatusBfdUnexpDiscr          Unsigned32,
    gamMepStatusBfdExpSrcMepIdTlv      OCTET STRING,
    gamMepStatusBfdUnexpSrcMepIdTlv    OCTET STRING,
    gamMepStatusBfdMyDiscr1            Unsigned32,
    gamMepStatusBfdRemoteDiscr1        Unsigned32
}

gamMepStatusBfdId OBJECT-TYPE
    SYNTAX      Integer32 (1..2147483647)
    MAX-ACCESS  accessible-for-notify
    STATUS      current
    DESCRIPTION
        "The MEP instance ID"
    ::= { gamMepStatusBfdEntry 1 }

gamMepStatusBfdCcTxCnt OBJECT-TYPE
    SYNTAX      GAMUnsigned64
    MAX-ACCESS  read-only
    STATUS      current
    DESCRIPTION
        "BFD CC transmitted."
    ::= { gamMepStatusBfdEntry 3 }

gamMepStatusBfdValidCcRxCnt OBJECT-TYPE
    SYNTAX      GAMUnsigned64
    MAX-ACCESS  read-only
    STATUS      current
    DESCRIPTION
        "Valid BFD CC received."
    ::= { gamMepStatusBfdEntry 4 }

gamMepStatusBfdInvalidCcRxCnt OBJECT-TYPE
    SYNTAX      GAMUnsigned64
    MAX-ACCESS  read-only
    STATUS      current
    DESCRIPTION
        "Invalid BFD CC received."
    ::= { gamMepStatusBfdEntry 5 }

gamMepStatusBfdCvTxCnt OBJECT-TYPE
    SYNTAX      GAMUnsigned64
    MAX-ACCESS  read-only
    STATUS      current
    DESCRIPTION
        "BFD CV transmitted."
    ::= { gamMepStatusBfdEntry 6 }

gamMepStatusBfdValidCvRxCnt OBJECT-TYPE
    SYNTAX      GAMUnsigned64
    MAX-ACCESS  read-only
    STATUS      current
    DESCRIPTION
        "Valid BFD CV received."
    ::= { gamMepStatusBfdEntry 7 }

gamMepStatusBfdInvalidCvRxCnt OBJECT-TYPE
    SYNTAX      GAMUnsigned64
    MAX-ACCESS  read-only
    STATUS      current
    DESCRIPTION
        "Invalid BFD CV received."
    ::= { gamMepStatusBfdEntry 8 }

gamMepStatusBfdMyDiscr OBJECT-TYPE
    SYNTAX      Unsigned32
    MAX-ACCESS  read-only
    STATUS      current
    DESCRIPTION
        "Selected random 'My Discriminator' value, non-zero."
    ::= { gamMepStatusBfdEntry 9 }

gamMepStatusBfdSessionState0 OBJECT-TYPE
    SYNTAX      GAMMepBfdSessionState
    MAX-ACCESS  read-only
    STATUS      current
    DESCRIPTION
        "Local BFD session state (for coordinated mode only SessionState0 is
         valid, for independent mode SessionState0 is sink, SessionState1 is
         source."
    ::= { gamMepStatusBfdEntry 10 }

gamMepStatusBfdSessionState1 OBJECT-TYPE
    SYNTAX      GAMMepBfdSessionState
    MAX-ACCESS  read-only
    STATUS      current
    DESCRIPTION
        "Local BFD session state. Only valid in independent mode where
         SessionState0 is sink, SessionState1 is source."
    ::= { gamMepStatusBfdEntry 11 }

gamMepStatusBfdLocalDiag OBJECT-TYPE
    SYNTAX      GAMMepBfdDiagnosticCode
    MAX-ACCESS  read-only
    STATUS      current
    DESCRIPTION
        "Local diagnostic code."
    ::= { gamMepStatusBfdEntry 12 }

gamMepStatusBfdRemoteSessionState OBJECT-TYPE
    SYNTAX      GAMMepBfdSessionState
    MAX-ACCESS  read-only
    STATUS      current
    DESCRIPTION
        "BFD session state received from remote end."
    ::= { gamMepStatusBfdEntry 13 }

gamMepStatusBfdRemoteDiag OBJECT-TYPE
    SYNTAX      GAMMepBfdDiagnosticCode
    MAX-ACCESS  read-only
    STATUS      current
    DESCRIPTION
        "Diagnostic code received from remote end."
    ::= { gamMepStatusBfdEntry 14 }

gamMepStatusBfdRemoteDiscr OBJECT-TYPE
    SYNTAX      Unsigned32
    MAX-ACCESS  read-only
    STATUS      current
    DESCRIPTION
        "Discriminator value received from remote end."
    ::= { gamMepStatusBfdEntry 15 }

gamMepStatusBfdRemoteMinRx OBJECT-TYPE
    SYNTAX      Unsigned32
    MAX-ACCESS  read-only
    STATUS      current
    DESCRIPTION
        "Required Min RX interval value received from remote end."
    ::= { gamMepStatusBfdEntry 16 }

gamMepStatusBfdRemoteFlags OBJECT-TYPE
    SYNTAX      GAMUnsigned8
    MAX-ACCESS  read-only
    STATUS      current
    DESCRIPTION
        "Flags received from remote end."
    ::= { gamMepStatusBfdEntry 17 }

gamMepStatusBfdUnexpDiscr OBJECT-TYPE
    SYNTAX      Unsigned32
    MAX-ACCESS  read-only
    STATUS      current
    DESCRIPTION
        "Last received unexpected discriminator value (should be my configured)."
    ::= { gamMepStatusBfdEntry 18 }

gamMepStatusBfdExpSrcMepIdTlv OBJECT-TYPE
    SYNTAX      OCTET STRING (SIZE(28))
    MAX-ACCESS  read-only
    STATUS      current
    DESCRIPTION
        "Expected source MEP ID TLV."
    ::= { gamMepStatusBfdEntry 19 }

gamMepStatusBfdUnexpSrcMepIdTlv OBJECT-TYPE
    SYNTAX      OCTET STRING (SIZE(28))
    MAX-ACCESS  read-only
    STATUS      current
    DESCRIPTION
        "Last received unexpected source MEP ID TLV."
    ::= { gamMepStatusBfdEntry 20 }

gamMepStatusBfdMyDiscr1 OBJECT-TYPE
    SYNTAX      Unsigned32
    MAX-ACCESS  read-only
    STATUS      current
    DESCRIPTION
        "Selected random 'My Discriminator' value (sink), non-zero. Only valid
         in independent mode."
    ::= { gamMepStatusBfdEntry 21 }

gamMepStatusBfdRemoteDiscr1 OBJECT-TYPE
    SYNTAX      Unsigned32
    MAX-ACCESS  read-only
    STATUS      current
    DESCRIPTION
        "Discriminator value received from remote end by sink. Only valid in
         independent mode."
    ::= { gamMepStatusBfdEntry 22 }

gamMepStatusRt OBJECT IDENTIFIER
    ::= { gamMepStatus 9 }

gamMepStatusRtTable OBJECT-TYPE
    SYNTAX      SEQUENCE OF GAMMepStatusRtEntry
    MAX-ACCESS  not-accessible
    STATUS      current
    DESCRIPTION
        "This is a table of Route Trace status"
    ::= { gamMepStatusRt 1 }

gamMepStatusRtEntry OBJECT-TYPE
    SYNTAX      GAMMepStatusRtEntry
    MAX-ACCESS  not-accessible
    STATUS      current
    DESCRIPTION
        "This is a Route Trace status"
    INDEX       { gamMepStatusRtId }
    ::= { gamMepStatusRtTable 1 }

GAMMepStatusRtEntry ::= SEQUENCE {
    gamMepStatusRtId            Integer32,
    gamMepStatusRtSeqNo         Unsigned32,
    gamMepStatusRtRequestCount  Unsigned32,
    gamMepStatusRtReplyCount    Unsigned32
}

gamMepStatusRtId OBJECT-TYPE
    SYNTAX      Integer32 (1..2147483647)
    MAX-ACCESS  accessible-for-notify
    STATUS      current
    DESCRIPTION
        "The MEP instance ID"
    ::= { gamMepStatusRtEntry 1 }

gamMepStatusRtSeqNo OBJECT-TYPE
    SYNTAX      Unsigned32
    MAX-ACCESS  read-only
    STATUS      current
    DESCRIPTION
        "Sequence number of first RT request."
    ::= { gamMepStatusRtEntry 2 }

gamMepStatusRtRequestCount OBJECT-TYPE
    SYNTAX      Unsigned32
    MAX-ACCESS  read-only
    STATUS      current
    DESCRIPTION
        "Number of RT requests sent for current session."
    ::= { gamMepStatusRtEntry 3 }

gamMepStatusRtReplyCount OBJECT-TYPE
    SYNTAX      Unsigned32
    MAX-ACCESS  read-only
    STATUS      current
    DESCRIPTION
        "Number of replies received for this Route Trace session."
    ::= { gamMepStatusRtEntry 4 }

gamMepStatusRtReplyTable OBJECT-TYPE
    SYNTAX      SEQUENCE OF GAMMepStatusRtReplyEntry
    MAX-ACCESS  not-accessible
    STATUS      current
    DESCRIPTION
        "This is a table of Route Trace reply status"
    ::= { gamMepStatusRt 2 }

gamMepStatusRtReplyEntry OBJECT-TYPE
    SYNTAX      GAMMepStatusRtReplyEntry
    MAX-ACCESS  not-accessible
    STATUS      current
    DESCRIPTION
        "This is a Route Trace reply status"
    INDEX       { gamMepStatusRtReplyId, gamMepStatusRtReplySeqNo }
    ::= { gamMepStatusRtReplyTable 1 }

GAMMepStatusRtReplyEntry ::= SEQUENCE {
    gamMepStatusRtReplyId              Integer32,
    gamMepStatusRtReplySeqNo           Unsigned32,
    gamMepStatusRtReplyReturnCode      GAMMepRtReturnCode,
    gamMepStatusRtReplyReturnSubcode   GAMUnsigned8,
    gamMepStatusRtReplyRttSec          Unsigned32,
    gamMepStatusRtReplyRttUsec         Unsigned32,
    gamMepStatusRtReplyTsSentSec       Unsigned32,
    gamMepStatusRtReplyTsSentUsec      Unsigned32,
    gamMepStatusRtReplyTsReceivedSec   Unsigned32,
    gamMepStatusRtReplyTsReceivedUsec  Unsigned32,
    gamMepStatusRtReplySrcGlobalId     Unsigned32,
    gamMepStatusRtReplySrcNodeId       IpAddress,
    gamMepStatusRtReplyFecSrcValue     Unsigned32,
    gamMepStatusRtReplyRxIfNum         Unsigned32,
    gamMepStatusRtReplyRxLabelCnt      Unsigned32,
    gamMepStatusRtReplyRxLabel1        Unsigned32,
    gamMepStatusRtReplyRxLabel2        Unsigned32,
    gamMepStatusRtReplyRxLabel3        Unsigned32,
    gamMepStatusRtReplyRxLabel4        Unsigned32,
    gamMepStatusRtReplyRxLabel5        Unsigned32,
    gamMepStatusRtReplyRxLabel6        Unsigned32,
    gamMepStatusRtReplyRxLabel7        Unsigned32,
    gamMepStatusRtReplyRxLabel8        Unsigned32
}

gamMepStatusRtReplyId OBJECT-TYPE
    SYNTAX      Integer32 (1..2147483647)
    MAX-ACCESS  accessible-for-notify
    STATUS      current
    DESCRIPTION
        "The MEP instance ID"
    ::= { gamMepStatusRtReplyEntry 1 }

gamMepStatusRtReplySeqNo OBJECT-TYPE
    SYNTAX      Unsigned32 (0..4294967295)
    MAX-ACCESS  accessible-for-notify
    STATUS      current
    DESCRIPTION
        "The RT sequence number"
    ::= { gamMepStatusRtReplyEntry 2 }

gamMepStatusRtReplyReturnCode OBJECT-TYPE
    SYNTAX      GAMMepRtReturnCode
    MAX-ACCESS  read-only
    STATUS      current
    DESCRIPTION
        "Return code from reply."
    ::= { gamMepStatusRtReplyEntry 3 }

gamMepStatusRtReplyReturnSubcode OBJECT-TYPE
    SYNTAX      GAMUnsigned8
    MAX-ACCESS  read-only
    STATUS      current
    DESCRIPTION
        "Return subcode from reply."
    ::= { gamMepStatusRtReplyEntry 4 }

gamMepStatusRtReplyRttSec OBJECT-TYPE
    SYNTAX      Unsigned32
    MAX-ACCESS  read-only
    STATUS      current
    DESCRIPTION
        "Round Trip Time (seconds)."
    ::= { gamMepStatusRtReplyEntry 5 }

gamMepStatusRtReplyRttUsec OBJECT-TYPE
    SYNTAX      Unsigned32
    MAX-ACCESS  read-only
    STATUS      current
    DESCRIPTION
        "Round Trip Time (microseconds)."
    ::= { gamMepStatusRtReplyEntry 6 }

gamMepStatusRtReplyTsSentSec OBJECT-TYPE
    SYNTAX      Unsigned32
    MAX-ACCESS  read-only
    STATUS      current
    DESCRIPTION
        "Timestamp sent (sender, seconds)."
    ::= { gamMepStatusRtReplyEntry 7 }

gamMepStatusRtReplyTsSentUsec OBJECT-TYPE
    SYNTAX      Unsigned32
    MAX-ACCESS  read-only
    STATUS      current
    DESCRIPTION
        "Timestamp sent (sender, microseconds)."
    ::= { gamMepStatusRtReplyEntry 8 }

gamMepStatusRtReplyTsReceivedSec OBJECT-TYPE
    SYNTAX      Unsigned32
    MAX-ACCESS  read-only
    STATUS      current
    DESCRIPTION
        "Timestamp received (receiver, seconds)."
    ::= { gamMepStatusRtReplyEntry 9 }

gamMepStatusRtReplyTsReceivedUsec OBJECT-TYPE
    SYNTAX      Unsigned32
    MAX-ACCESS  read-only
    STATUS      current
    DESCRIPTION
        "Timestamp received (receiver, microseconds)."
    ::= { gamMepStatusRtReplyEntry 10 }

gamMepStatusRtReplySrcGlobalId OBJECT-TYPE
    SYNTAX      Unsigned32
    MAX-ACCESS  read-only
    STATUS      current
    DESCRIPTION
        "Source global ID from received FEC or source ID TLV in RT reply."
    ::= { gamMepStatusRtReplyEntry 11 }

gamMepStatusRtReplySrcNodeId OBJECT-TYPE
    SYNTAX      IpAddress
    MAX-ACCESS  read-only
    STATUS      current
    DESCRIPTION
        "Source node ID from received FEC or source ID TLV in RT reply."
    ::= { gamMepStatusRtReplyEntry 12 }

gamMepStatusRtReplyFecSrcValue OBJECT-TYPE
    SYNTAX      Unsigned32
    MAX-ACCESS  read-only
    STATUS      current
    DESCRIPTION
        "For a reply from a PW MEP this is the source AC-ID from the received
         FEC in the RT reply. For a Tunnel MEP or LSP MIP bit 31:16 is the
         source tunnel number and bit 15:0 is the LSP number from the received
         FEC in the RT reply."
    ::= { gamMepStatusRtReplyEntry 13 }

gamMepStatusRtReplyRxIfNum OBJECT-TYPE
    SYNTAX      Unsigned32
    MAX-ACCESS  read-only
    STATUS      current
    DESCRIPTION
        "Receiver local interface index from reply."
    ::= { gamMepStatusRtReplyEntry 14 }

gamMepStatusRtReplyRxLabelCnt OBJECT-TYPE
    SYNTAX      Unsigned32
    MAX-ACCESS  read-only
    STATUS      current
    DESCRIPTION
        "Number of valid label values RxLabel1, RxLabel2 etc."
    ::= { gamMepStatusRtReplyEntry 15 }

gamMepStatusRtReplyRxLabel1 OBJECT-TYPE
    SYNTAX      Unsigned32
    MAX-ACCESS  read-only
    STATUS      current
    DESCRIPTION
        "1st MPLS label (top label) of Label Stack of RT request as seen by
         receiver."
    ::= { gamMepStatusRtReplyEntry 16 }

gamMepStatusRtReplyRxLabel2 OBJECT-TYPE
    SYNTAX      Unsigned32
    MAX-ACCESS  read-only
    STATUS      current
    DESCRIPTION
        "2nd MPLS label of Label Stack of RT request as seen by receiver."
    ::= { gamMepStatusRtReplyEntry 17 }

gamMepStatusRtReplyRxLabel3 OBJECT-TYPE
    SYNTAX      Unsigned32
    MAX-ACCESS  read-only
    STATUS      current
    DESCRIPTION
        "3rd MPLS label of Label Stack of RT request as seen by receiver."
    ::= { gamMepStatusRtReplyEntry 18 }

gamMepStatusRtReplyRxLabel4 OBJECT-TYPE
    SYNTAX      Unsigned32
    MAX-ACCESS  read-only
    STATUS      current
    DESCRIPTION
        "4th MPLS label of Label Stack of RT request as seen by receiver."
    ::= { gamMepStatusRtReplyEntry 19 }

gamMepStatusRtReplyRxLabel5 OBJECT-TYPE
    SYNTAX      Unsigned32
    MAX-ACCESS  read-only
    STATUS      current
    DESCRIPTION
        "5th MPLS label of Label Stack of RT request as seen by receiver."
    ::= { gamMepStatusRtReplyEntry 20 }

gamMepStatusRtReplyRxLabel6 OBJECT-TYPE
    SYNTAX      Unsigned32
    MAX-ACCESS  read-only
    STATUS      current
    DESCRIPTION
        "6th MPLS label of Label Stack of RT request as seen by receiver."
    ::= { gamMepStatusRtReplyEntry 21 }

gamMepStatusRtReplyRxLabel7 OBJECT-TYPE
    SYNTAX      Unsigned32
    MAX-ACCESS  read-only
    STATUS      current
    DESCRIPTION
        "7th MPLS label of Label Stack of RT request as seen by receiver."
    ::= { gamMepStatusRtReplyEntry 22 }

gamMepStatusRtReplyRxLabel8 OBJECT-TYPE
    SYNTAX      Unsigned32
    MAX-ACCESS  read-only
    STATUS      current
    DESCRIPTION
        "8th MPLS label of Label Stack of RT request as seen by receiver."
    ::= { gamMepStatusRtReplyEntry 23 }

gamMepStatusLmAvail OBJECT IDENTIFIER
    ::= { gamMepStatus 10 }

gamMepStatusLmAvailTable OBJECT-TYPE
    SYNTAX      SEQUENCE OF GAMMepStatusLmAvailEntry
    MAX-ACCESS  not-accessible
    STATUS      current
    DESCRIPTION
        "This is a table of Loss Measurement Availability status"
    ::= { gamMepStatusLmAvail 2 }

gamMepStatusLmAvailEntry OBJECT-TYPE
    SYNTAX      GAMMepStatusLmAvailEntry
    MAX-ACCESS  not-accessible
    STATUS      current
    DESCRIPTION
        "This is a Loss Measurement Availability status"
    INDEX       { gamMepStatusLmAvailId, gamMepStatusLmAvailPeerId }
    ::= { gamMepStatusLmAvailTable 1 }

GAMMepStatusLmAvailEntry ::= SEQUENCE {
    gamMepStatusLmAvailId                 Integer32,
    gamMepStatusLmAvailPeerId             Integer32,
    gamMepStatusLmAvailNearEndAvailState  GAMMepLmAvailState,
    gamMepStatusLmAvailFarEndAvailState   GAMMepLmAvailState,
    gamMepStatusLmAvailNearEndAvailCnt    Unsigned32,
    gamMepStatusLmAvailFarEndAvailCnt     Unsigned32,
    gamMepStatusLmAvailNearEndUnAvailCnt  Unsigned32,
    gamMepStatusLmAvailFarEndUnAvailCnt   Unsigned32,
    gamMepStatusLmAvailNearEndWindowCnt   Unsigned32,
    gamMepStatusLmAvailFarEndWindowCnt    Unsigned32
}

gamMepStatusLmAvailId OBJECT-TYPE
    SYNTAX      Integer32 (1..2147483647)
    MAX-ACCESS  accessible-for-notify
    STATUS      current
    DESCRIPTION
        "The MEP instance ID"
    ::= { gamMepStatusLmAvailEntry 1 }

gamMepStatusLmAvailPeerId OBJECT-TYPE
    SYNTAX      Integer32 (0..2147483647)
    MAX-ACCESS  accessible-for-notify
    STATUS      current
    DESCRIPTION
        "The Peer MEP ID"
    ::= { gamMepStatusLmAvailEntry 2 }

gamMepStatusLmAvailNearEndAvailState OBJECT-TYPE
    SYNTAX      GAMMepLmAvailState
    MAX-ACCESS  read-only
    STATUS      current
    DESCRIPTION
        "Near end Availability State."
    ::= { gamMepStatusLmAvailEntry 3 }

gamMepStatusLmAvailFarEndAvailState OBJECT-TYPE
    SYNTAX      GAMMepLmAvailState
    MAX-ACCESS  read-only
    STATUS      current
    DESCRIPTION
        "Far end Availability State."
    ::= { gamMepStatusLmAvailEntry 4 }

gamMepStatusLmAvailNearEndAvailCnt OBJECT-TYPE
    SYNTAX      Unsigned32
    MAX-ACCESS  read-only
    STATUS      current
    DESCRIPTION
        "Near end Availability Count."
    ::= { gamMepStatusLmAvailEntry 5 }

gamMepStatusLmAvailFarEndAvailCnt OBJECT-TYPE
    SYNTAX      Unsigned32
    MAX-ACCESS  read-only
    STATUS      current
    DESCRIPTION
        "Far end Availability Count."
    ::= { gamMepStatusLmAvailEntry 6 }

gamMepStatusLmAvailNearEndUnAvailCnt OBJECT-TYPE
    SYNTAX      Unsigned32
    MAX-ACCESS  read-only
    STATUS      current
    DESCRIPTION
        "Near end Unavailability Count."
    ::= { gamMepStatusLmAvailEntry 7 }

gamMepStatusLmAvailFarEndUnAvailCnt OBJECT-TYPE
    SYNTAX      Unsigned32
    MAX-ACCESS  read-only
    STATUS      current
    DESCRIPTION
        "Far end Unavailability Count."
    ::= { gamMepStatusLmAvailEntry 8 }

gamMepStatusLmAvailNearEndWindowCnt OBJECT-TYPE
    SYNTAX      Unsigned32
    MAX-ACCESS  read-only
    STATUS      current
    DESCRIPTION
        "Near end Window Count."
    ::= { gamMepStatusLmAvailEntry 9 }

gamMepStatusLmAvailFarEndWindowCnt OBJECT-TYPE
    SYNTAX      Unsigned32
    MAX-ACCESS  read-only
    STATUS      current
    DESCRIPTION
        "Far end Window Count."
    ::= { gamMepStatusLmAvailEntry 10 }

gamMepStatusLmHli OBJECT IDENTIFIER
    ::= { gamMepStatus 11 }

gamMepStatusLmHliTable OBJECT-TYPE
    SYNTAX      SEQUENCE OF GAMMepStatusLmHliEntry
    MAX-ACCESS  not-accessible
    STATUS      current
    DESCRIPTION
        "This is a table of Loss Measurement High Loss Interval status"
    ::= { gamMepStatusLmHli 1 }

gamMepStatusLmHliEntry OBJECT-TYPE
    SYNTAX      GAMMepStatusLmHliEntry
    MAX-ACCESS  not-accessible
    STATUS      current
    DESCRIPTION
        "This is a Loss Measurement High Loss Interval status"
    INDEX       { gamMepStatusLmHliId, gamMepStatusLmHliPeerId }
    ::= { gamMepStatusLmHliTable 1 }

GAMMepStatusLmHliEntry ::= SEQUENCE {
    gamMepStatusLmHliId             Integer32,
    gamMepStatusLmHliPeerId         Integer32,
    gamMepStatusLmHliNearEndCnt     Unsigned32,
    gamMepStatusLmHliFarEndCnt      Unsigned32,
    gamMepStatusLmHliNearEndConCnt  Unsigned32,
    gamMepStatusLmHliFarEndConCnt   Unsigned32
}

gamMepStatusLmHliId OBJECT-TYPE
    SYNTAX      Integer32 (1..2147483647)
    MAX-ACCESS  accessible-for-notify
    STATUS      current
    DESCRIPTION
        "The MEP instance ID"
    ::= { gamMepStatusLmHliEntry 1 }

gamMepStatusLmHliPeerId OBJECT-TYPE
    SYNTAX      Integer32 (0..2147483647)
    MAX-ACCESS  accessible-for-notify
    STATUS      current
    DESCRIPTION
        "The Peer MEP ID"
    ::= { gamMepStatusLmHliEntry 2 }

gamMepStatusLmHliNearEndCnt OBJECT-TYPE
    SYNTAX      Unsigned32
    MAX-ACCESS  read-only
    STATUS      current
    DESCRIPTION
        "Near end High Loss Interval count (number of measurements where
         Availability State is available and FLR is above HLI FLR threshold."
    ::= { gamMepStatusLmHliEntry 3 }

gamMepStatusLmHliFarEndCnt OBJECT-TYPE
    SYNTAX      Unsigned32
    MAX-ACCESS  read-only
    STATUS      current
    DESCRIPTION
        "Far end High Loss Interval count (number of measurements where
         Availability State is available and FLR is above HLI FLR threshold."
    ::= { gamMepStatusLmHliEntry 4 }

gamMepStatusLmHliNearEndConCnt OBJECT-TYPE
    SYNTAX      Unsigned32
    MAX-ACCESS  read-only
    STATUS      current
    DESCRIPTION
        "Near end High Loss Interval consecutive count."
    ::= { gamMepStatusLmHliEntry 5 }

gamMepStatusLmHliFarEndConCnt OBJECT-TYPE
    SYNTAX      Unsigned32
    MAX-ACCESS  read-only
    STATUS      current
    DESCRIPTION
        "Far end High Loss Interval consecutive count."
    ::= { gamMepStatusLmHliEntry 6 }

gamMepStatusDmBinFd OBJECT IDENTIFIER
    ::= { gamMepStatus 12 }

gamMepStatusDmBinFdTable OBJECT-TYPE
    SYNTAX      SEQUENCE OF GAMMepStatusDmBinFdEntry
    MAX-ACCESS  not-accessible
    STATUS      current
    DESCRIPTION
        "This is a table of Delay Measurement Bin Fd status"
    ::= { gamMepStatusDmBinFd 1 }

gamMepStatusDmBinFdEntry OBJECT-TYPE
    SYNTAX      GAMMepStatusDmBinFdEntry
    MAX-ACCESS  not-accessible
    STATUS      current
    DESCRIPTION
        "This is a Delay Measurement Bin Fd status"
    INDEX       { gamMepStatusDmBinFdId,
                  gamMepStatusDmBinFdBinIndexId }
    ::= { gamMepStatusDmBinFdTable 1 }

GAMMepStatusDmBinFdEntry ::= SEQUENCE {
    gamMepStatusDmBinFdId          Integer32,
    gamMepStatusDmBinFdBinIndexId  Integer32,
    gamMepStatusDmBinFdFdBin       Integer32,
    gamMepStatusDmBinFdTwValue     Unsigned32,
    gamMepStatusDmBinFdOwFtNValue  Unsigned32,
    gamMepStatusDmBinFdOwNtFValue  Unsigned32
}

gamMepStatusDmBinFdId OBJECT-TYPE
    SYNTAX      Integer32 (1..2147483647)
    MAX-ACCESS  accessible-for-notify
    STATUS      current
    DESCRIPTION
        "The MEP instance ID"
    ::= { gamMepStatusDmBinFdEntry 1 }

gamMepStatusDmBinFdBinIndexId OBJECT-TYPE
    SYNTAX      Integer32 (0..9)
    MAX-ACCESS  accessible-for-notify
    STATUS      current
    DESCRIPTION
        "FD or IFDV Bin index ID"
    ::= { gamMepStatusDmBinFdEntry 2 }

gamMepStatusDmBinFdFdBin OBJECT-TYPE
    SYNTAX      Integer32
    MAX-ACCESS  read-only
    STATUS      current
    DESCRIPTION
        "FD bin value (two-way). This object is deprecated and contains the same
         value as the TwValue object below."
    ::= { gamMepStatusDmBinFdEntry 3 }

gamMepStatusDmBinFdTwValue OBJECT-TYPE
    SYNTAX      Unsigned32
    MAX-ACCESS  read-only
    STATUS      current
    DESCRIPTION
        "Value for two-way bin."
    ::= { gamMepStatusDmBinFdEntry 4 }

gamMepStatusDmBinFdOwFtNValue OBJECT-TYPE
    SYNTAX      Unsigned32
    MAX-ACCESS  read-only
    STATUS      current
    DESCRIPTION
        "Value for one-way far-to-near bin."
    ::= { gamMepStatusDmBinFdEntry 5 }

gamMepStatusDmBinFdOwNtFValue OBJECT-TYPE
    SYNTAX      Unsigned32
    MAX-ACCESS  read-only
    STATUS      current
    DESCRIPTION
        "Value for one-way near-to-far bin."
    ::= { gamMepStatusDmBinFdEntry 6 }

gamMepStatusDmBinIfdv OBJECT IDENTIFIER
    ::= { gamMepStatus 13 }

gamMepStatusDmBinIfdvTable OBJECT-TYPE
    SYNTAX      SEQUENCE OF GAMMepStatusDmBinIfdvEntry
    MAX-ACCESS  not-accessible
    STATUS      current
    DESCRIPTION
        "This is a table of Delay Measurement Bin Ifdv status"
    ::= { gamMepStatusDmBinIfdv 1 }

gamMepStatusDmBinIfdvEntry OBJECT-TYPE
    SYNTAX      GAMMepStatusDmBinIfdvEntry
    MAX-ACCESS  not-accessible
    STATUS      current
    DESCRIPTION
        "This is a Delay Measurement Bin Ifdv status"
    INDEX       { gamMepStatusDmBinIfdvId,
                  gamMepStatusDmBinIfdvBinIndexId }
    ::= { gamMepStatusDmBinIfdvTable 1 }

GAMMepStatusDmBinIfdvEntry ::= SEQUENCE {
    gamMepStatusDmBinIfdvId          Integer32,
    gamMepStatusDmBinIfdvBinIndexId  Integer32,
    gamMepStatusDmBinIfdvIfdvBin     Integer32,
    gamMepStatusDmBinIfdvTwValue     Unsigned32,
    gamMepStatusDmBinIfdvOwFtNValue  Unsigned32,
    gamMepStatusDmBinIfdvOwNtFValue  Unsigned32
}

gamMepStatusDmBinIfdvId OBJECT-TYPE
    SYNTAX      Integer32 (1..2147483647)
    MAX-ACCESS  accessible-for-notify
    STATUS      current
    DESCRIPTION
        "The MEP instance ID"
    ::= { gamMepStatusDmBinIfdvEntry 1 }

gamMepStatusDmBinIfdvBinIndexId OBJECT-TYPE
    SYNTAX      Integer32 (0..9)
    MAX-ACCESS  accessible-for-notify
    STATUS      current
    DESCRIPTION
        "FD or IFDV Bin index ID"
    ::= { gamMepStatusDmBinIfdvEntry 2 }

gamMepStatusDmBinIfdvIfdvBin OBJECT-TYPE
    SYNTAX      Integer32
    MAX-ACCESS  read-only
    STATUS      current
    DESCRIPTION
        "IFDV bin value (two-way). This object is deprecated and contains the
         same value as the TwValue object below."
    ::= { gamMepStatusDmBinIfdvEntry 3 }

gamMepStatusDmBinIfdvTwValue OBJECT-TYPE
    SYNTAX      Unsigned32
    MAX-ACCESS  read-only
    STATUS      current
    DESCRIPTION
        "Value for two-way bin."
    ::= { gamMepStatusDmBinIfdvEntry 4 }

gamMepStatusDmBinIfdvOwFtNValue OBJECT-TYPE
    SYNTAX      Unsigned32
    MAX-ACCESS  read-only
    STATUS      current
    DESCRIPTION
        "Value for one-way far-to-near bin."
    ::= { gamMepStatusDmBinIfdvEntry 5 }

gamMepStatusDmBinIfdvOwNtFValue OBJECT-TYPE
    SYNTAX      Unsigned32
    MAX-ACCESS  read-only
    STATUS      current
    DESCRIPTION
        "Value for one-way near-to-far bin."
    ::= { gamMepStatusDmBinIfdvEntry 6 }

gamMepControl OBJECT IDENTIFIER
    ::= { gamMepMibObjects 4 }

gamMepControlLm OBJECT IDENTIFIER
    ::= { gamMepControl 1 }

gamMepControlLmTable OBJECT-TYPE
    SYNTAX      SEQUENCE OF GAMMepControlLmEntry
    MAX-ACCESS  not-accessible
    STATUS      current
    DESCRIPTION
        "This is a table of created instance Loss Measurement control parameters"
    ::= { gamMepControlLm 1 }

gamMepControlLmEntry OBJECT-TYPE
    SYNTAX      GAMMepControlLmEntry
    MAX-ACCESS  not-accessible
    STATUS      current
    DESCRIPTION
        "This is a created instance Loss Measurement control parameters"
    INDEX       { gamMepControlLmId }
    ::= { gamMepControlLmTable 1 }

GAMMepControlLmEntry ::= SEQUENCE {
    gamMepControlLmId     Integer32,
    gamMepControlLmClear  TruthValue
}

gamMepControlLmId OBJECT-TYPE
    SYNTAX      Integer32 (1..2147483647)
    MAX-ACCESS  accessible-for-notify
    STATUS      current
    DESCRIPTION
        "The MEP instance ID"
    ::= { gamMepControlLmEntry 1 }

gamMepControlLmClear OBJECT-TYPE
    SYNTAX      TruthValue
    MAX-ACCESS  read-write
    STATUS      current
    DESCRIPTION
        "Clear the LM results"
    ::= { gamMepControlLmEntry 2 }

gamMepControlDm OBJECT IDENTIFIER
    ::= { gamMepControl 2 }

gamMepControlDmTable OBJECT-TYPE
    SYNTAX      SEQUENCE OF GAMMepControlDmEntry
    MAX-ACCESS  not-accessible
    STATUS      current
    DESCRIPTION
        "This is a table of created instance Delay Measurement control
         parameters"
    ::= { gamMepControlDm 1 }

gamMepControlDmEntry OBJECT-TYPE
    SYNTAX      GAMMepControlDmEntry
    MAX-ACCESS  not-accessible
    STATUS      current
    DESCRIPTION
        "This is a created instance Delay Measurement control parameters"
    INDEX       { gamMepControlDmId }
    ::= { gamMepControlDmTable 1 }

GAMMepControlDmEntry ::= SEQUENCE {
    gamMepControlDmId     Integer32,
    gamMepControlDmClear  TruthValue
}

gamMepControlDmId OBJECT-TYPE
    SYNTAX      Integer32 (1..2147483647)
    MAX-ACCESS  accessible-for-notify
    STATUS      current
    DESCRIPTION
        "The MEP instance ID"
    ::= { gamMepControlDmEntry 1 }

gamMepControlDmClear OBJECT-TYPE
    SYNTAX      TruthValue
    MAX-ACCESS  read-write
    STATUS      current
    DESCRIPTION
        "Clear the DM results"
    ::= { gamMepControlDmEntry 2 }

gamMepControlTst OBJECT IDENTIFIER
    ::= { gamMepControl 3 }

gamMepControlTstTable OBJECT-TYPE
    SYNTAX      SEQUENCE OF GAMMepControlTstEntry
    MAX-ACCESS  not-accessible
    STATUS      current
    DESCRIPTION
        "This is a table of created instance Test Signal control parameters"
    ::= { gamMepControlTst 1 }

gamMepControlTstEntry OBJECT-TYPE
    SYNTAX      GAMMepControlTstEntry
    MAX-ACCESS  not-accessible
    STATUS      current
    DESCRIPTION
        "This is a created instance Test Signal control parameters"
    INDEX       { gamMepControlTstId }
    ::= { gamMepControlTstTable 1 }

GAMMepControlTstEntry ::= SEQUENCE {
    gamMepControlTstId     Integer32,
    gamMepControlTstClear  TruthValue
}

gamMepControlTstId OBJECT-TYPE
    SYNTAX      Integer32 (1..2147483647)
    MAX-ACCESS  accessible-for-notify
    STATUS      current
    DESCRIPTION
        "The MEP instance ID"
    ::= { gamMepControlTstEntry 1 }

gamMepControlTstClear OBJECT-TYPE
    SYNTAX      TruthValue
    MAX-ACCESS  read-write
    STATUS      current
    DESCRIPTION
        "Clear the TST results"
    ::= { gamMepControlTstEntry 2 }

gamMepControlBfd OBJECT IDENTIFIER
    ::= { gamMepControl 4 }

gamMepControlBfdTable OBJECT-TYPE
    SYNTAX      SEQUENCE OF GAMMepControlBfdEntry
    MAX-ACCESS  not-accessible
    STATUS      current
    DESCRIPTION
        "This is a table of created instance BFD control parameters"
    ::= { gamMepControlBfd 1 }

gamMepControlBfdEntry OBJECT-TYPE
    SYNTAX      GAMMepControlBfdEntry
    MAX-ACCESS  not-accessible
    STATUS      current
    DESCRIPTION
        "This is a created instance BFD control parameters"
    INDEX       { gamMepControlBfdId }
    ::= { gamMepControlBfdTable 1 }

GAMMepControlBfdEntry ::= SEQUENCE {
    gamMepControlBfdId     Integer32,
    gamMepControlBfdClear  TruthValue
}

gamMepControlBfdId OBJECT-TYPE
    SYNTAX      Integer32 (1..2147483647)
    MAX-ACCESS  accessible-for-notify
    STATUS      current
    DESCRIPTION
        "The MEP instance ID"
    ::= { gamMepControlBfdEntry 1 }

gamMepControlBfdClear OBJECT-TYPE
    SYNTAX      TruthValue
    MAX-ACCESS  read-write
    STATUS      current
    DESCRIPTION
        "Clear the BFD statistics counters"
    ::= { gamMepControlBfdEntry 2 }

gamMepMibConformance OBJECT IDENTIFIER
    ::= { gamMepMib 2 }

gamMepMibCompliances OBJECT IDENTIFIER
    ::= { gamMepMibConformance 1 }

gamMepMibGroups OBJECT IDENTIFIER
    ::= { gamMepMibConformance 2 }

gamMepCapabilitiesInfoGroup OBJECT-GROUP
    OBJECTS     { gamMepCapabilitiesInstanceMax,
                  gamMepCapabilitiesPeerMax,
                  gamMepCapabilitiesTransactionMax,
                  gamMepCapabilitiesReplyMax,
                  gamMepCapabilitiesClientFlowsMax,
                  gamMepCapabilitiesMacMength,
                  gamMepCapabilitiesMegCodeLength,
                  gamMepCapabilitiesDmIntervalMin,
                  gamMepCapabilitiesDmIntervalMax,
                  gamMepCapabilitiesDmLastnMin,
                  gamMepCapabilitiesDmLastnMax,
                  gamMepCapabilitiesLbmSizeMax,
                  gamMepCapabilitiesLbmSizeMin,
                  gamMepCapabilitiesTstSizeMax,
                  gamMepCapabilitiesTstSizeMin,
                  gamMepCapabilitiesTstRateMax,
                  gamMepCapabilitiesClientPrioHighest,
                  gamMepCapabilitiesItuG8113dot2,
                  gamMepCapabilitiesVoeSupport,
                  gamMepCapabilitiesLbToSendInfinite,
                  gamMepCapabilitiesBfdAuthKeyMax,
                  gamMepCapabilitiesHasEvcPag,
                  gamMepCapabilitiesHasEvcQos,
                  gamMepCapabilitiesHasFlowCount,
                  gamMepCapabilitiesHasOamCount,
                  gamMepCapabilitiesHasOperState,
                  gamMepCapabilitiesHasOamSwSupport }
    STATUS      current
    DESCRIPTION
        "A collection of objects."
    ::= { gamMepMibGroups 1 }

gamMepConfigInstanceTableInfoGroup OBJECT-GROUP
    OBJECTS     { gamMepConfigInstanceId, gamMepConfigInstanceMode,
                  gamMepConfigInstanceDirection,
                  gamMepConfigInstanceFlow, gamMepConfigInstancePort,
                  gamMepConfigInstanceLevel, gamMepConfigInstanceVid,
                  gamMepConfigInstanceVoe, gamMepConfigInstanceMac,
                  gamMepConfigInstanceFormat,
                  gamMepConfigInstanceName, gamMepConfigInstanceMeg,
                  gamMepConfigInstanceMep, gamMepConfigInstanceEvcPag,
                  gamMepConfigInstanceEvcQos,
                  gamMepConfigInstanceAction }
    STATUS      current
    DESCRIPTION
        "A collection of objects."
    ::= { gamMepMibGroups 2 }

gamMepConfigInstanceRowEditorInfoGroup OBJECT-GROUP
    OBJECTS     { gamMepConfigInstanceRowEditorId,
                  gamMepConfigInstanceRowEditorMode,
                  gamMepConfigInstanceRowEditorDirection,
                  gamMepConfigInstanceRowEditorFlow,
                  gamMepConfigInstanceRowEditorPort,
                  gamMepConfigInstanceRowEditorLevel,
                  gamMepConfigInstanceRowEditorVid,
                  gamMepConfigInstanceRowEditorVoe,
                  gamMepConfigInstanceRowEditorMac,
                  gamMepConfigInstanceRowEditorFormat,
                  gamMepConfigInstanceRowEditorName,
                  gamMepConfigInstanceRowEditorMeg,
                  gamMepConfigInstanceRowEditorMep,
                  gamMepConfigInstanceRowEditorEvcPag,
                  gamMepConfigInstanceRowEditorEvcQos,
                  gamMepConfigInstanceRowEditorAction }
    STATUS      current
    DESCRIPTION
        "A collection of objects."
    ::= { gamMepMibGroups 3 }

gamMepConfigInstancePeerTableInfoGroup OBJECT-GROUP
    OBJECTS     { gamMepConfigInstancePeerId,
                  gamMepConfigInstancePeerPeerId,
                  gamMepConfigInstancePeerMac,
                  gamMepConfigInstancePeerAction }
    STATUS      current
    DESCRIPTION
        "A collection of objects."
    ::= { gamMepMibGroups 4 }

gamMepConfigInstancePeerRowEditorInfoGroup OBJECT-GROUP
    OBJECTS     { gamMepConfigInstancePeerRowEditorId,
                  gamMepConfigInstancePeerRowEditorPeerId,
                  gamMepConfigInstancePeerRowEditorMac,
                  gamMepConfigInstancePeerRowEditorAction }
    STATUS      current
    DESCRIPTION
        "A collection of objects."
    ::= { gamMepMibGroups 5 }

gamMepConfigPmTableInfoGroup OBJECT-GROUP
    OBJECTS     { gamMepConfigPmId, gamMepConfigPmEnable }
    STATUS      current
    DESCRIPTION
        "A collection of objects."
    ::= { gamMepMibGroups 6 }

gamMepConfigCcTableInfoGroup OBJECT-GROUP
    OBJECTS     { gamMepConfigCcId, gamMepConfigCcPrio,
                  gamMepConfigCcRate, gamMepConfigCcTlv,
                  gamMepConfigCcAction }
    STATUS      current
    DESCRIPTION
        "A collection of objects."
    ::= { gamMepMibGroups 7 }

gamMepConfigCcRowEditorInfoGroup OBJECT-GROUP
    OBJECTS     { gamMepConfigCcRowEditorId,
                  gamMepConfigCcRowEditorPrio,
                  gamMepConfigCcRowEditorRate,
                  gamMepConfigCcRowEditorTlv,
                  gamMepConfigCcRowEditorAction }
    STATUS      current
    DESCRIPTION
        "A collection of objects."
    ::= { gamMepMibGroups 8 }

gamMepConfigLmTableInfoGroup OBJECT-GROUP
    OBJECTS     { gamMepConfigLmId, gamMepConfigLmEnable,
                  gamMepConfigLmEnded, gamMepConfigLmPrio,
                  gamMepConfigLmRate, gamMepConfigLmCast,
                  gamMepConfigLmFlrInterval, gamMepConfigLmFlowCount,
                  gamMepConfigLmOamCount, gamMepConfigLmLossTh,
                  gamMepConfigLmLossCounterIntHolddownTimer,
                  gamMepConfigLmLossThCntHolddownTimer,
                  gamMepConfigLmRxEnable, gamMepConfigLmSynthetic,
                  gamMepConfigLmMep, gamMepConfigLmFrameSize,
                  gamMepConfigLmMeasInterval, gamMepConfigLmSlmTestId }
    STATUS      current
    DESCRIPTION
        "A collection of objects."
    ::= { gamMepMibGroups 9 }

gamMepConfigDmTableInfoGroup OBJECT-GROUP
    OBJECTS     { gamMepConfigDmId, gamMepConfigDmEnable,
                  gamMepConfigDmEnded, gamMepConfigDmPrio,
                  gamMepConfigDmCast, gamMepConfigDmMep,
                  gamMepConfigDmCalcWay, gamMepConfigDmInterval,
                  gamMepConfigDmLastN, gamMepConfigDmTimeUnit,
                  gamMepConfigDmOverflowAct,
                  gamMepConfigDmSynchronized,
                  gamMepConfigDmNumOfBinFD,
                  gamMepConfigDmNumOfBinIFDV,
                  gamMepConfigDmMThreshold }
    STATUS      current
    DESCRIPTION
        "A collection of objects."
    ::= { gamMepMibGroups 10 }

gamMepConfigLbTableInfoGroup OBJECT-GROUP
    OBJECTS     { gamMepConfigLbId, gamMepConfigLbDei,
                  gamMepConfigLbPrio, gamMepConfigLbCast,
                  gamMepConfigLbMep, gamMepConfigLbMac,
                  gamMepConfigLbToSend, gamMepConfigLbSize,
                  gamMepConfigLbInterval, gamMepConfigLbTimeToLive,
                  gamMepConfigLbAction }
    STATUS      current
    DESCRIPTION
        "A collection of objects."
    ::= { gamMepMibGroups 11 }

gamMepConfigLbRowEditorInfoGroup OBJECT-GROUP
    OBJECTS     { gamMepConfigLbRowEditorId,
                  gamMepConfigLbRowEditorDei,
                  gamMepConfigLbRowEditorPrio,
                  gamMepConfigLbRowEditorCast,
                  gamMepConfigLbRowEditorMep,
                  gamMepConfigLbRowEditorMac,
                  gamMepConfigLbRowEditorToSend,
                  gamMepConfigLbRowEditorSize,
                  gamMepConfigLbRowEditorInterval,
                  gamMepConfigLbRowEditorTimeToLive,
                  gamMepConfigLbRowEditorAction }
    STATUS      current
    DESCRIPTION
        "A collection of objects."
    ::= { gamMepMibGroups 12 }

gamMepConfigTstTableInfoGroup OBJECT-GROUP
    OBJECTS     { gamMepConfigTstId, gamMepConfigTstTxEnable,
                  gamMepConfigTstRxEnable, gamMepConfigTstDei,
                  gamMepConfigTstPrio, gamMepConfigTstMep,
                  gamMepConfigTstRate, gamMepConfigTstSize,
                  gamMepConfigTstPattern, gamMepConfigTstSequence,
                  gamMepConfigTstAction }
    STATUS      current
    DESCRIPTION
        "A collection of objects."
    ::= { gamMepMibGroups 13 }

gamMepConfigTstRowEditorInfoGroup OBJECT-GROUP
    OBJECTS     { gamMepConfigTstRowEditorId,
                  gamMepConfigTstRowEditorTxEnable,
                  gamMepConfigTstRowEditorRxEnable,
                  gamMepConfigTstRowEditorDei,
                  gamMepConfigTstRowEditorPrio,
                  gamMepConfigTstRowEditorMep,
                  gamMepConfigTstRowEditorRate,
                  gamMepConfigTstRowEditorSize,
                  gamMepConfigTstRowEditorPattern,
                  gamMepConfigTstRowEditorSequence,
                  gamMepConfigTstRowEditorAction }
    STATUS      current
    DESCRIPTION
        "A collection of objects."
    ::= { gamMepMibGroups 14 }

gamMepConfigLtTableInfoGroup OBJECT-GROUP
    OBJECTS     { gamMepConfigLtId, gamMepConfigLtPrio,
                  gamMepConfigLtMep, gamMepConfigLtMac,
                  gamMepConfigLtTimeToLive, gamMepConfigLtAction }
    STATUS      current
    DESCRIPTION
        "A collection of objects."
    ::= { gamMepMibGroups 15 }

gamMepConfigLtRowEditorInfoGroup OBJECT-GROUP
    OBJECTS     { gamMepConfigLtRowEditorId,
                  gamMepConfigLtRowEditorPrio,
                  gamMepConfigLtRowEditorMep,
                  gamMepConfigLtRowEditorMac,
                  gamMepConfigLtRowEditorTimeToLive,
                  gamMepConfigLtRowEditorAction }
    STATUS      current
    DESCRIPTION
        "A collection of objects."
    ::= { gamMepMibGroups 16 }

gamMepConfigApsTableInfoGroup OBJECT-GROUP
    OBJECTS     { gamMepConfigApsId, gamMepConfigApsPrio,
                  gamMepConfigApsApsType, gamMepConfigApsCast,
                  gamMepConfigApsRapsOctet, gamMepConfigApsAction }
    STATUS      current
    DESCRIPTION
        "A collection of objects."
    ::= { gamMepMibGroups 17 }

gamMepConfigApsRowEditorInfoGroup OBJECT-GROUP
    OBJECTS     { gamMepConfigApsRowEditorId,
                  gamMepConfigApsRowEditorPrio,
                  gamMepConfigApsRowEditorApsType,
                  gamMepConfigApsRowEditorCast,
                  gamMepConfigApsRowEditorRapsOctet,
                  gamMepConfigApsRowEditorAction }
    STATUS      current
    DESCRIPTION
        "A collection of objects."
    ::= { gamMepMibGroups 18 }

gamMepConfigAisTableInfoGroup OBJECT-GROUP
    OBJECTS     { gamMepConfigAisId, gamMepConfigAisProtection,
                  gamMepConfigAisRate, gamMepConfigAisAction }
    STATUS      current
    DESCRIPTION
        "A collection of objects."
    ::= { gamMepMibGroups 19 }

gamMepConfigAisRowEditorInfoGroup OBJECT-GROUP
    OBJECTS     { gamMepConfigAisRowEditorId,
                  gamMepConfigAisRowEditorProtection,
                  gamMepConfigAisRowEditorRate,
                  gamMepConfigAisRowEditorAction }
    STATUS      current
    DESCRIPTION
        "A collection of objects."
    ::= { gamMepMibGroups 20 }

gamMepConfigLckTableInfoGroup OBJECT-GROUP
    OBJECTS     { gamMepConfigLckId, gamMepConfigLckRate,
                  gamMepConfigLckAction }
    STATUS      current
    DESCRIPTION
        "A collection of objects."
    ::= { gamMepMibGroups 21 }

gamMepConfigLckRowEditorInfoGroup OBJECT-GROUP
    OBJECTS     { gamMepConfigLckRowEditorId,
                  gamMepConfigLckRowEditorRate,
                  gamMepConfigLckRowEditorAction }
    STATUS      current
    DESCRIPTION
        "A collection of objects."
    ::= { gamMepMibGroups 22 }

gamMepConfigClientFlowTableInfoGroup OBJECT-GROUP
    OBJECTS     { gamMepConfigClientFlowId,
                  gamMepConfigClientFlowFlowId,
                  gamMepConfigClientFlowAisPrio,
                  gamMepConfigClientFlowLckPrio,
                  gamMepConfigClientFlowLevel,
                  gamMepConfigClientFlowAction }
    STATUS      current
    DESCRIPTION
        "A collection of objects."
    ::= { gamMepMibGroups 23 }

gamMepConfigClientFlowRowEditorInfoGroup OBJECT-GROUP
    OBJECTS     { gamMepConfigClientFlowRowEditorId,
                  gamMepConfigClientFlowRowEditorFlowId,
                  gamMepConfigClientFlowRowEditorAisPrio,
                  gamMepConfigClientFlowRowEditorLckPrio,
                  gamMepConfigClientFlowRowEditorLevel,
                  gamMepConfigClientFlowRowEditorAction }
    STATUS      current
    DESCRIPTION
        "A collection of objects."
    ::= { gamMepMibGroups 24 }

gamMepConfigSyslogTableInfoGroup OBJECT-GROUP
    OBJECTS     { gamMepConfigSyslogId, gamMepConfigSyslogEnable }
    STATUS      current
    DESCRIPTION
        "A collection of objects."
    ::= { gamMepMibGroups 25 }

gamMepConfigTlvLeafInfoGroup OBJECT-GROUP
    OBJECTS     { gamMepConfigTlvLeafOsTlvOuiFirst,
                  gamMepConfigTlvLeafOsTlvOuiSecond,
                  gamMepConfigTlvLeafOsTlvOuiThird,
                  gamMepConfigTlvLeafOsTlvSubType,
                  gamMepConfigTlvLeafOsTlvValue }
    STATUS      current
    DESCRIPTION
        "A collection of objects."
    ::= { gamMepMibGroups 26 }

gamMepConfigBfdTableInfoGroup OBJECT-GROUP
    OBJECTS     { gamMepConfigBfdId, gamMepConfigBfdEnable,
                  gamMepConfigBfdIsIndependent, gamMepConfigBfdCcOnly,
                  gamMepConfigBfdTxAuthEnabled,
                  gamMepConfigBfdRxAuthEnabled,
                  gamMepConfigBfdTxAuthKeyId, gamMepConfigBfdCcPeriod,
                  gamMepConfigBfdRxFlow, gamMepConfigBfdAction }
    STATUS      current
    DESCRIPTION
        "A collection of objects."
    ::= { gamMepMibGroups 27 }

gamMepConfigBfdRowEditorInfoGroup OBJECT-GROUP
    OBJECTS     { gamMepConfigBfdRowEditorId,
                  gamMepConfigBfdRowEditorEnable,
                  gamMepConfigBfdRowEditorIsIndependent,
                  gamMepConfigBfdRowEditorCcOnly,
                  gamMepConfigBfdRowEditorTxAuthEnabled,
                  gamMepConfigBfdRowEditorRxAuthEnabled,
                  gamMepConfigBfdRowEditorTxAuthKeyId,
                  gamMepConfigBfdRowEditorCcPeriod,
                  gamMepConfigBfdRowEditorRxFlow,
                  gamMepConfigBfdRowEditorAction }
    STATUS      current
    DESCRIPTION
        "A collection of objects."
    ::= { gamMepMibGroups 28 }

gamMepConfigBfdAuthTableInfoGroup OBJECT-GROUP
    OBJECTS     { gamMepConfigBfdAuthId, gamMepConfigBfdAuthKeyType,
                  gamMepConfigBfdAuthKeyLen, gamMepConfigBfdAuthKey,
                  gamMepConfigBfdAuthAction }
    STATUS      current
    DESCRIPTION
        "A collection of objects."
    ::= { gamMepMibGroups 29 }

gamMepConfigBfdAuthRowEditorInfoGroup OBJECT-GROUP
    OBJECTS     { gamMepConfigBfdAuthRowEditorId,
                  gamMepConfigBfdAuthRowEditorKeyType,
                  gamMepConfigBfdAuthRowEditorKeyLen,
                  gamMepConfigBfdAuthRowEditorKey,
                  gamMepConfigBfdAuthRowEditorAction }
    STATUS      current
    DESCRIPTION
        "A collection of objects."
    ::= { gamMepMibGroups 30 }

gamMepConfigRtTableInfoGroup OBJECT-GROUP
    OBJECTS     { gamMepConfigRtId, gamMepConfigRtTrafficClass,
                  gamMepConfigRtSrcIdTlv, gamMepConfigRtDstIdTlv,
                  gamMepConfigRtPadTlvType, gamMepConfigRtPadTlvLen,
                  gamMepConfigRtFlags, gamMepConfigRtMaxTimeToLive,
                  gamMepConfigRtAction }
    STATUS      current
    DESCRIPTION
        "A collection of objects."
    ::= { gamMepMibGroups 31 }

gamMepConfigRtRowEditorInfoGroup OBJECT-GROUP
    OBJECTS     { gamMepConfigRtRowEditorId,
                  gamMepConfigRtRowEditorTrafficClass,
                  gamMepConfigRtRowEditorSrcIdTlv,
                  gamMepConfigRtRowEditorDstIdTlv,
                  gamMepConfigRtRowEditorPadTlvType,
                  gamMepConfigRtRowEditorPadTlvLen,
                  gamMepConfigRtRowEditorFlags,
                  gamMepConfigRtRowEditorMaxTimeToLive,
                  gamMepConfigRtRowEditorAction }
    STATUS      current
    DESCRIPTION
        "A collection of objects."
    ::= { gamMepMibGroups 32 }

gamMepConfigLstTableInfoGroup OBJECT-GROUP
    OBJECTS     { gamMepConfigLstId, gamMepConfigLstEnable }
    STATUS      current
    DESCRIPTION
        "A collection of objects."
    ::= { gamMepMibGroups 33 }

gamMepConfigLmAvailTableInfoGroup OBJECT-GROUP
    OBJECTS     { gamMepConfigLmAvailId, gamMepConfigLmAvailEnable,
                  gamMepConfigLmAvailLosRatioThr,
                  gamMepConfigLmAvailInterval,
                  gamMepConfigLmAvailMaintenance }
    STATUS      current
    DESCRIPTION
        "A collection of objects."
    ::= { gamMepMibGroups 34 }

gamMepConfigLmHliTableInfoGroup OBJECT-GROUP
    OBJECTS     { gamMepConfigLmHliId, gamMepConfigLmHliEnable,
                  gamMepConfigLmHliHiLosRatioThr,
                  gamMepConfigLmHliConInterval,
                  gamMepConfigLmHliCntHolddownTimer }
    STATUS      current
    DESCRIPTION
        "A collection of objects."
    ::= { gamMepMibGroups 35 }

gamMepConfigLmSdegTableInfoGroup OBJECT-GROUP
    OBJECTS     { gamMepConfigLmSdegId, gamMepConfigLmSdegEnable,
                  gamMepConfigLmSdegTxMin,
                  gamMepConfigLmSdegLosRatioThr,
                  gamMepConfigLmSdegBadThr, gamMepConfigLmSdegGoodThr }
    STATUS      current
    DESCRIPTION
        "A collection of objects."
    ::= { gamMepMibGroups 36 }

gamMepStatusInstanceTableInfoGroup OBJECT-GROUP
    OBJECTS     { gamMepStatusInstanceId, gamMepStatusInstanceClevel,
                  gamMepStatusInstanceCmeg, gamMepStatusInstanceCmep,
                  gamMepStatusInstanceCssf, gamMepStatusInstanceCais,
                  gamMepStatusInstanceClck, gamMepStatusInstanceAtsf,
                  gamMepStatusInstanceAtsd, gamMepStatusInstanceAblk,
                  gamMepStatusInstanceCloop,
                  gamMepStatusInstanceCconfig,
                  gamMepStatusInstanceCdeg,
                  gamMepStatusInstanceOperState }
    STATUS      current
    DESCRIPTION
        "A collection of objects."
    ::= { gamMepMibGroups 37 }

gamMepStatusInstancePeerTableInfoGroup OBJECT-GROUP
    OBJECTS     { gamMepStatusInstancePeerId,
                  gamMepStatusInstancePeerPeerId,
                  gamMepStatusInstancePeerCloc,
                  gamMepStatusInstancePeerCrdi,
                  gamMepStatusInstancePeerCperiod,
                  gamMepStatusInstancePeerCprio }
    STATUS      current
    DESCRIPTION
        "A collection of objects."
    ::= { gamMepMibGroups 38 }

gamMepStatusLmTableInfoGroup OBJECT-GROUP
    OBJECTS     { gamMepStatusLmId, gamMepStatusLmTxCounter,
                  gamMepStatusLmRxCounter,
                  gamMepStatusLmNearEndLosCounterTot,
                  gamMepStatusLmFarEndLosCounterTot,
                  gamMepStatusLmNearEndLosRatioInt,
                  gamMepStatusLmFarEndLosRatioInt,
                  gamMepStatusLmNearEndLosCounterInt,
                  gamMepStatusLmFarEndLosCounterInt,
                  gamMepStatusLmNearEndLosThCnt,
                  gamMepStatusLmFarEndLosThCnt,
                  gamMepStatusLmNearEndLosRatioTot,
                  gamMepStatusLmFarEndLosRatioTot,
                  gamMepStatusLmNearEndLosRatioMin,
                  gamMepStatusLmFarEndLosRatioMin,
                  gamMepStatusLmNearEndLosRatioMax,
                  gamMepStatusLmFarEndLosRatioMax,
                  gamMepStatusLmElapsedIntervals }
    STATUS      current
    DESCRIPTION
        "A collection of objects."
    ::= { gamMepMibGroups 39 }

gamMepStatusLmPeerTableInfoGroup OBJECT-GROUP
    OBJECTS     { gamMepStatusLmPeerId, gamMepStatusLmPeerPeerId,
                  gamMepStatusLmPeerTxCounter,
                  gamMepStatusLmPeerRxCounter,
                  gamMepStatusLmPeerNearEndLosCounterTot,
                  gamMepStatusLmPeerFarEndLosCounterTot,
                  gamMepStatusLmPeerNearEndLosRatioInt,
                  gamMepStatusLmPeerFarEndLosRatioInt,
                  gamMepStatusLmPeerNearEndLosCounterInt,
                  gamMepStatusLmPeerFarEndLosCounterInt,
                  gamMepStatusLmPeerNearEndLosThCnt,
                  gamMepStatusLmPeerFarEndLosThCnt,
                  gamMepStatusLmPeerNearEndLosRatioTot,
                  gamMepStatusLmPeerFarEndLosRatioTot,
                  gamMepStatusLmPeerNearEndLosRatioMin,
                  gamMepStatusLmPeerFarEndLosRatioMin,
                  gamMepStatusLmPeerNearEndLosRatioMax,
                  gamMepStatusLmPeerFarEndLosRatioMax,
                  gamMepStatusLmPeerElapsedIntervals }
    STATUS      current
    DESCRIPTION
        "A collection of objects."
    ::= { gamMepMibGroups 40 }

gamMepStatusDmTwoWayTableInfoGroup OBJECT-GROUP
    OBJECTS     { gamMepStatusDmTwoWayId,
                  gamMepStatusDmTwoWayTxCounter,
                  gamMepStatusDmTwoWayRxCounter,
                  gamMepStatusDmTwoWayRxTimeOutCounter,
                  gamMepStatusDmTwoWayRxErrorCounter,
                  gamMepStatusDmTwoWayInternalOverflowCounter,
                  gamMepStatusDmTwoWayAverageDelay,
                  gamMepStatusDmTwoWayAverageLastnDelay,
                  gamMepStatusDmTwoWayAverageDelayVariation,
                  gamMepStatusDmTwoWayAverageLastnDelayVariation,
                  gamMepStatusDmTwoWayMinimumDelay,
                  gamMepStatusDmTwoWayMaximumDelay,
                  gamMepStatusDmTwoWayMinimumDelayVariation,
                  gamMepStatusDmTwoWayMaximumDelayVariation,
                  gamMepStatusDmTwoWayTimeUnit }
    STATUS      current
    DESCRIPTION
        "A collection of objects."
    ::= { gamMepMibGroups 41 }

gamMepStatusDmOneWayFarNearTableInfoGroup OBJECT-GROUP
    OBJECTS     { gamMepStatusDmOneWayFarNearId,
                  gamMepStatusDmOneWayFarNearTxCounter,
                  gamMepStatusDmOneWayFarNearRxCounter,
                  gamMepStatusDmOneWayFarNearRxTimeOutCounter,
                  gamMepStatusDmOneWayFarNearRxErrorCounter,
                  gamMepStatusDmOneWayFarNearInternalOverflowCounter,
                  gamMepStatusDmOneWayFarNearAverageDelay,
                  gamMepStatusDmOneWayFarNearAverageLastnDelay,
                  gamMepStatusDmOneWayFarNearAverageDelayVariation,
                  gamMepStatusDmOneWayFarNearAverageLastnDelayVariation,
                  gamMepStatusDmOneWayFarNearMinimumDelay,
                  gamMepStatusDmOneWayFarNearMaximumDelay,
                  gamMepStatusDmOneWayFarNearMinimumDelayVariation,
                  gamMepStatusDmOneWayFarNearMaximumDelayVariation,
                  gamMepStatusDmOneWayFarNearTimeUnit }
    STATUS      current
    DESCRIPTION
        "A collection of objects."
    ::= { gamMepMibGroups 42 }

gamMepStatusDmOneWayNearFarTableInfoGroup OBJECT-GROUP
    OBJECTS     { gamMepStatusDmOneWayNearFarId,
                  gamMepStatusDmOneWayNearFarTxCounter,
                  gamMepStatusDmOneWayNearFarRxCounter,
                  gamMepStatusDmOneWayNearFarRxTimeOutCounter,
                  gamMepStatusDmOneWayNearFarRxErrorCounter,
                  gamMepStatusDmOneWayNearFarInternalOverflowCounter,
                  gamMepStatusDmOneWayNearFarAverageDelay,
                  gamMepStatusDmOneWayNearFarAverageLastnDelay,
                  gamMepStatusDmOneWayNearFarAverageDelayVariation,
                  gamMepStatusDmOneWayNearFarAverageLastnDelayVariation,
                  gamMepStatusDmOneWayNearFarMinimumDelay,
                  gamMepStatusDmOneWayNearFarMaximumDelay,
                  gamMepStatusDmOneWayNearFarMinimumDelayVariation,
                  gamMepStatusDmOneWayNearFarMaximumDelayVariation,
                  gamMepStatusDmOneWayNearFarTimeUnit }
    STATUS      current
    DESCRIPTION
        "A collection of objects."
    ::= { gamMepMibGroups 43 }

gamMepStatusLbTableInfoGroup OBJECT-GROUP
    OBJECTS     { gamMepStatusLbId, gamMepStatusLbTransactionId,
                  gamMepStatusLbReplyCounter,
                  gamMepStatusLbLbmTransmitted }
    STATUS      current
    DESCRIPTION
        "A collection of objects."
    ::= { gamMepMibGroups 44 }

gamMepStatusLbReplyTableInfoGroup OBJECT-GROUP
    OBJECTS     { gamMepStatusLbReplyId, gamMepStatusLbReplyReplyId,
                  gamMepStatusLbReplyMac,
                  gamMepStatusLbReplyLbrReceived,
                  gamMepStatusLbReplyOutOfOrder,
                  gamMepStatusLbReplyMepMipId }
    STATUS      current
    DESCRIPTION
        "A collection of objects."
    ::= { gamMepMibGroups 45 }

gamMepStatusTstTableInfoGroup OBJECT-GROUP
    OBJECTS     { gamMepStatusTstId, gamMepStatusTstTxCounter,
                  gamMepStatusTstRxCounter,
                  gamMepStatusTstOutOfOrderCounter,
                  gamMepStatusTstRxRate, gamMepStatusTstTestTime }
    STATUS      current
    DESCRIPTION
        "A collection of objects."
    ::= { gamMepMibGroups 46 }

gamMepStatusLtTableInfoGroup OBJECT-GROUP
    OBJECTS     { gamMepStatusLtId, gamMepStatusLtTransactionId,
                  gamMepStatusLtReplyCount }
    STATUS      current
    DESCRIPTION
        "A collection of objects."
    ::= { gamMepMibGroups 47 }

gamMepStatusLtReplyTableInfoGroup OBJECT-GROUP
    OBJECTS     { gamMepStatusLtReplyId, gamMepStatusLtReplyReplyId,
                  gamMepStatusLtReplyMode,
                  gamMepStatusLtReplyDirection,
                  gamMepStatusLtReplyTtl,
                  gamMepStatusLtReplyForwarded,
                  gamMepStatusLtReplyRelayAction,
                  gamMepStatusLtReplyLastEgressMac,
                  gamMepStatusLtReplyNextEgressMac }
    STATUS      current
    DESCRIPTION
        "A collection of objects."
    ::= { gamMepMibGroups 48 }

gamMepStatusCcPeerTableInfoGroup OBJECT-GROUP
    OBJECTS     { gamMepStatusCcPeerId, gamMepStatusCcPeerPeerId,
                  gamMepStatusCcPeerOsTlvOuiFirst,
                  gamMepStatusCcPeerOsTlvOuiSecond,
                  gamMepStatusCcPeerOsTlvOuiThird,
                  gamMepStatusCcPeerOsTlvSubType,
                  gamMepStatusCcPeerOsTlvValue,
                  gamMepStatusCcPeerIsTlvValue,
                  gamMepStatusCcPeerPsTlvValue,
                  gamMepStatusCcPeerOsTlvReceived,
                  gamMepStatusCcPeerIsTlvReceived,
                  gamMepStatusCcPeerPsTlvReceived }
    STATUS      current
    DESCRIPTION
        "A collection of objects."
    ::= { gamMepMibGroups 49 }

gamMepStatusBfdTableInfoGroup OBJECT-GROUP
    OBJECTS     { gamMepStatusBfdId, gamMepStatusBfdCcTxCnt,
                  gamMepStatusBfdValidCcRxCnt,
                  gamMepStatusBfdInvalidCcRxCnt,
                  gamMepStatusBfdCvTxCnt, gamMepStatusBfdValidCvRxCnt,
                  gamMepStatusBfdInvalidCvRxCnt,
                  gamMepStatusBfdMyDiscr,
                  gamMepStatusBfdSessionState0,
                  gamMepStatusBfdSessionState1,
                  gamMepStatusBfdLocalDiag,
                  gamMepStatusBfdRemoteSessionState,
                  gamMepStatusBfdRemoteDiag,
                  gamMepStatusBfdRemoteDiscr,
                  gamMepStatusBfdRemoteMinRx,
                  gamMepStatusBfdRemoteFlags,
                  gamMepStatusBfdUnexpDiscr,
                  gamMepStatusBfdExpSrcMepIdTlv,
                  gamMepStatusBfdUnexpSrcMepIdTlv,
                  gamMepStatusBfdMyDiscr1,
                  gamMepStatusBfdRemoteDiscr1 }
    STATUS      current
    DESCRIPTION
        "A collection of objects."
    ::= { gamMepMibGroups 50 }

gamMepStatusRtTableInfoGroup OBJECT-GROUP
    OBJECTS     { gamMepStatusRtId, gamMepStatusRtSeqNo,
                  gamMepStatusRtRequestCount,
                  gamMepStatusRtReplyCount }
    STATUS      current
    DESCRIPTION
        "A collection of objects."
    ::= { gamMepMibGroups 51 }

gamMepStatusRtReplyTableInfoGroup OBJECT-GROUP
    OBJECTS     { gamMepStatusRtReplyId, gamMepStatusRtReplySeqNo,
                  gamMepStatusRtReplyReturnCode,
                  gamMepStatusRtReplyReturnSubcode,
                  gamMepStatusRtReplyRttSec,
                  gamMepStatusRtReplyRttUsec,
                  gamMepStatusRtReplyTsSentSec,
                  gamMepStatusRtReplyTsSentUsec,
                  gamMepStatusRtReplyTsReceivedSec,
                  gamMepStatusRtReplyTsReceivedUsec,
                  gamMepStatusRtReplySrcGlobalId,
                  gamMepStatusRtReplySrcNodeId,
                  gamMepStatusRtReplyFecSrcValue,
                  gamMepStatusRtReplyRxIfNum,
                  gamMepStatusRtReplyRxLabelCnt,
                  gamMepStatusRtReplyRxLabel1,
                  gamMepStatusRtReplyRxLabel2,
                  gamMepStatusRtReplyRxLabel3,
                  gamMepStatusRtReplyRxLabel4,
                  gamMepStatusRtReplyRxLabel5,
                  gamMepStatusRtReplyRxLabel6,
                  gamMepStatusRtReplyRxLabel7,
                  gamMepStatusRtReplyRxLabel8 }
    STATUS      current
    DESCRIPTION
        "A collection of objects."
    ::= { gamMepMibGroups 52 }

gamMepStatusLmAvailTableInfoGroup OBJECT-GROUP
    OBJECTS     { gamMepStatusLmAvailId, gamMepStatusLmAvailPeerId,
                  gamMepStatusLmAvailNearEndAvailState,
                  gamMepStatusLmAvailFarEndAvailState,
                  gamMepStatusLmAvailNearEndAvailCnt,
                  gamMepStatusLmAvailFarEndAvailCnt,
                  gamMepStatusLmAvailNearEndUnAvailCnt,
                  gamMepStatusLmAvailFarEndUnAvailCnt,
                  gamMepStatusLmAvailNearEndWindowCnt,
                  gamMepStatusLmAvailFarEndWindowCnt }
    STATUS      current
    DESCRIPTION
        "A collection of objects."
    ::= { gamMepMibGroups 53 }

gamMepStatusLmHliTableInfoGroup OBJECT-GROUP
    OBJECTS     { gamMepStatusLmHliId, gamMepStatusLmHliPeerId,
                  gamMepStatusLmHliNearEndCnt,
                  gamMepStatusLmHliFarEndCnt,
                  gamMepStatusLmHliNearEndConCnt,
                  gamMepStatusLmHliFarEndConCnt }
    STATUS      current
    DESCRIPTION
        "A collection of objects."
    ::= { gamMepMibGroups 54 }

gamMepStatusDmBinFdTableInfoGroup OBJECT-GROUP
    OBJECTS     { gamMepStatusDmBinFdId,
                  gamMepStatusDmBinFdBinIndexId,
                  gamMepStatusDmBinFdFdBin,
                  gamMepStatusDmBinFdTwValue,
                  gamMepStatusDmBinFdOwFtNValue,
                  gamMepStatusDmBinFdOwNtFValue }
    STATUS      current
    DESCRIPTION
        "A collection of objects."
    ::= { gamMepMibGroups 55 }

gamMepStatusDmBinIfdvTableInfoGroup OBJECT-GROUP
    OBJECTS     { gamMepStatusDmBinIfdvId,
                  gamMepStatusDmBinIfdvBinIndexId,
                  gamMepStatusDmBinIfdvIfdvBin,
                  gamMepStatusDmBinIfdvTwValue,
                  gamMepStatusDmBinIfdvOwFtNValue,
                  gamMepStatusDmBinIfdvOwNtFValue }
    STATUS      current
    DESCRIPTION
        "A collection of objects."
    ::= { gamMepMibGroups 56 }

gamMepControlLmTableInfoGroup OBJECT-GROUP
    OBJECTS     { gamMepControlLmId, gamMepControlLmClear }
    STATUS      current
    DESCRIPTION
        "A collection of objects."
    ::= { gamMepMibGroups 57 }

gamMepControlDmTableInfoGroup OBJECT-GROUP
    OBJECTS     { gamMepControlDmId, gamMepControlDmClear }
    STATUS      current
    DESCRIPTION
        "A collection of objects."
    ::= { gamMepMibGroups 58 }

gamMepControlTstTableInfoGroup OBJECT-GROUP
    OBJECTS     { gamMepControlTstId, gamMepControlTstClear }
    STATUS      current
    DESCRIPTION
        "A collection of objects."
    ::= { gamMepMibGroups 59 }

gamMepControlBfdTableInfoGroup OBJECT-GROUP
    OBJECTS     { gamMepControlBfdId, gamMepControlBfdClear }
    STATUS      current
    DESCRIPTION
        "A collection of objects."
    ::= { gamMepMibGroups 60 }

gamMepMibCompliance MODULE-COMPLIANCE
    STATUS      current
    DESCRIPTION
        "The compliance statement for the implementation."

    MODULE      -- this module

    MANDATORY-GROUPS { gamMepCapabilitiesInfoGroup,
                       gamMepConfigInstanceTableInfoGroup,
                       gamMepConfigInstanceRowEditorInfoGroup,
                       gamMepConfigInstancePeerTableInfoGroup,
                       gamMepConfigInstancePeerRowEditorInfoGroup,
                       gamMepConfigPmTableInfoGroup,
                       gamMepConfigCcTableInfoGroup,
                       gamMepConfigCcRowEditorInfoGroup,
                       gamMepConfigLmTableInfoGroup,
                       gamMepConfigDmTableInfoGroup,
                       gamMepConfigLbTableInfoGroup,
                       gamMepConfigLbRowEditorInfoGroup,
                       gamMepConfigTstTableInfoGroup,
                       gamMepConfigTstRowEditorInfoGroup,
                       gamMepConfigLtTableInfoGroup,
                       gamMepConfigLtRowEditorInfoGroup,
                       gamMepConfigApsTableInfoGroup,
                       gamMepConfigApsRowEditorInfoGroup,
                       gamMepConfigAisTableInfoGroup,
                       gamMepConfigAisRowEditorInfoGroup,
                       gamMepConfigLckTableInfoGroup,
                       gamMepConfigLckRowEditorInfoGroup,
                       gamMepConfigClientFlowTableInfoGroup,
                       gamMepConfigClientFlowRowEditorInfoGroup,
                       gamMepConfigSyslogTableInfoGroup,
                       gamMepConfigTlvLeafInfoGroup,
                       gamMepConfigBfdTableInfoGroup,
                       gamMepConfigBfdRowEditorInfoGroup,
                       gamMepConfigBfdAuthTableInfoGroup,
                       gamMepConfigBfdAuthRowEditorInfoGroup,
                       gamMepConfigRtTableInfoGroup,
                       gamMepConfigRtRowEditorInfoGroup,
                       gamMepConfigLstTableInfoGroup,
                       gamMepConfigLmAvailTableInfoGroup,
                       gamMepConfigLmHliTableInfoGroup,
                       gamMepConfigLmSdegTableInfoGroup,
                       gamMepStatusInstanceTableInfoGroup,
                       gamMepStatusInstancePeerTableInfoGroup,
                       gamMepStatusLmTableInfoGroup,
                       gamMepStatusLmPeerTableInfoGroup,
                       gamMepStatusDmTwoWayTableInfoGroup,
                       gamMepStatusDmOneWayFarNearTableInfoGroup,
                       gamMepStatusDmOneWayNearFarTableInfoGroup,
                       gamMepStatusLbTableInfoGroup,
                       gamMepStatusLbReplyTableInfoGroup,
                       gamMepStatusTstTableInfoGroup,
                       gamMepStatusLtTableInfoGroup,
                       gamMepStatusLtReplyTableInfoGroup,
                       gamMepStatusCcPeerTableInfoGroup,
                       gamMepStatusBfdTableInfoGroup,
                       gamMepStatusRtTableInfoGroup,
                       gamMepStatusRtReplyTableInfoGroup,
                       gamMepStatusLmAvailTableInfoGroup,
                       gamMepStatusLmHliTableInfoGroup,
                       gamMepStatusDmBinFdTableInfoGroup,
                       gamMepStatusDmBinIfdvTableInfoGroup,
                       gamMepControlLmTableInfoGroup,
                       gamMepControlDmTableInfoGroup,
                       gamMepControlTstTableInfoGroup,
                       gamMepControlBfdTableInfoGroup }

    ::= { gamMepMibCompliances 1 }

END
