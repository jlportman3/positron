-- *****************************************************************
-- VLAN-TRANSLATION-MIB:  Positron's GAM private MIB
-- *****************************************************************

GAM-VLAN-TRANSLATION-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    gamMgmt FROM POSITRON-SMI
    GAMInterfaceIndex FROM GAM-TC
    GAMRowEditorState FROM GAM-TC
    Integer32 FROM SNMPv2-SMI
    Unsigned32 FROM SNMPv2-SMI
    ;

gamVlanTranslationMib MODULE-IDENTITY
    LAST-UPDATED "201406300000Z"
    ORGANIZATION
        "Positron Access Solutions Corp."
    CONTACT-INFO
        "Customer Service <info@positronaccess.com>"
    DESCRIPTION
        "Private VLAN TRANSLATION MIB."
    REVISION    "201406300000Z"
    DESCRIPTION
        "Initial version"
    ::= { gamMgmt 85 }


gamVlanTranslationMibObjects OBJECT IDENTIFIER
    ::= { gamVlanTranslationMib 1 }

gamVlanTranslationCapabilities OBJECT IDENTIFIER
    ::= { gamVlanTranslationMibObjects 1 }

gamVlanTranslationCapabilitiesMaxNumberOfTranslations OBJECT-TYPE
    SYNTAX      Unsigned32
    MAX-ACCESS  read-only
    STATUS      current
    DESCRIPTION
        "Maximum number of VLAN translation mappings the user can store in the
         VLAN Translation mapping table."
    ::= { gamVlanTranslationCapabilities 1 }

gamVlanTranslationConfig OBJECT IDENTIFIER
    ::= { gamVlanTranslationMibObjects 2 }

gamVlanTranslationConfigTranslation OBJECT IDENTIFIER
    ::= { gamVlanTranslationConfig 1 }

gamVlanTranslationConfigTranslationTable OBJECT-TYPE
    SYNTAX      SEQUENCE OF GAMVlanTranslationConfigTranslationEntry
    MAX-ACCESS  not-accessible
    STATUS      current
    DESCRIPTION
        "This is the VLAN translation mapping table.
         
         Here the user stores VLAN translation mappings (VID->TVID) inside
         groups that can later be activated on specific switch interfaces"
    ::= { gamVlanTranslationConfigTranslation 1 }

gamVlanTranslationConfigTranslationEntry OBJECT-TYPE
    SYNTAX      GAMVlanTranslationConfigTranslationEntry
    MAX-ACCESS  not-accessible
    STATUS      current
    DESCRIPTION
        "Each entry in this table represents a VLAN translation mapping stored
         inside a specific VLAN translation Group.
         
         The entry key is the Group ID and the source VLAN ID, while the value
         is the translated VID.
         
         "
    INDEX       { gamVlanTranslationConfigTranslationGroupId,
                  gamVlanTranslationConfigTranslationVlanId }
    ::= { gamVlanTranslationConfigTranslationTable 1 }

GAMVlanTranslationConfigTranslationEntry ::= SEQUENCE {
    gamVlanTranslationConfigTranslationGroupId  Integer32,
    gamVlanTranslationConfigTranslationVlanId   Integer32,
    gamVlanTranslationConfigTranslationTVlanId  Integer32,
    gamVlanTranslationConfigTranslationAction   GAMRowEditorState
}

gamVlanTranslationConfigTranslationGroupId OBJECT-TYPE
    SYNTAX      Integer32 (1..65535)
    MAX-ACCESS  accessible-for-notify
    STATUS      current
    DESCRIPTION
        "Group ID of the VLAN translation mapping key."
    ::= { gamVlanTranslationConfigTranslationEntry 1 }

gamVlanTranslationConfigTranslationVlanId OBJECT-TYPE
    SYNTAX      Integer32 (1..4095)
    MAX-ACCESS  accessible-for-notify
    STATUS      current
    DESCRIPTION
        "Vlan ID of the VLAN translation mapping key."
    ::= { gamVlanTranslationConfigTranslationEntry 2 }

gamVlanTranslationConfigTranslationTVlanId OBJECT-TYPE
    SYNTAX      Integer32 (1..4095)
    MAX-ACCESS  read-write
    STATUS      current
    DESCRIPTION
        "Translated VLAN ID of the VLAN translation mapping."
    ::= { gamVlanTranslationConfigTranslationEntry 3 }

gamVlanTranslationConfigTranslationAction OBJECT-TYPE
    SYNTAX      GAMRowEditorState
    MAX-ACCESS  read-write
    STATUS      current
    DESCRIPTION
        "Action"
    ::= { gamVlanTranslationConfigTranslationEntry 100 }

gamVlanTranslationConfigTranslationRowEditor OBJECT IDENTIFIER
    ::= { gamVlanTranslationConfigTranslation 2 }

gamVlanTranslationConfigTranslationRowEditorGroupId OBJECT-TYPE
    SYNTAX      Integer32 (1..65535)
    MAX-ACCESS  read-write
    STATUS      current
    DESCRIPTION
        "Group ID of the VLAN translation mapping key."
    ::= { gamVlanTranslationConfigTranslationRowEditor 1 }

gamVlanTranslationConfigTranslationRowEditorVlanId OBJECT-TYPE
    SYNTAX      Integer32 (1..4095)
    MAX-ACCESS  read-write
    STATUS      current
    DESCRIPTION
        "Vlan ID of the VLAN translation mapping key."
    ::= { gamVlanTranslationConfigTranslationRowEditor 2 }

gamVlanTranslationConfigTranslationRowEditorTVlanId OBJECT-TYPE
    SYNTAX      Integer32 (1..4095)
    MAX-ACCESS  read-write
    STATUS      current
    DESCRIPTION
        "Translated VLAN ID of the VLAN translation mapping."
    ::= { gamVlanTranslationConfigTranslationRowEditor 3 }

gamVlanTranslationConfigTranslationRowEditorAction OBJECT-TYPE
    SYNTAX      GAMRowEditorState
    MAX-ACCESS  read-write
    STATUS      current
    DESCRIPTION
        "Action"
    ::= { gamVlanTranslationConfigTranslationRowEditor 100 }

gamVlanTranslationConfigInterfaces OBJECT IDENTIFIER
    ::= { gamVlanTranslationConfig 2 }

gamVlanTranslationConfigInterfacesIfTable OBJECT-TYPE
    SYNTAX      SEQUENCE OF GAMVlanTranslationConfigInterfacesIfEntry
    MAX-ACCESS  not-accessible
    STATUS      current
    DESCRIPTION
        "This is the VLAN translation interface table. The number of interfaces
         is the total number of ports available on the switch. Each one of these
         interfaces can be set to use a specific Group of VLAN translation
         mappings, identified by the respective Group ID."
    ::= { gamVlanTranslationConfigInterfaces 1 }

gamVlanTranslationConfigInterfacesIfEntry OBJECT-TYPE
    SYNTAX      GAMVlanTranslationConfigInterfacesIfEntry
    MAX-ACCESS  not-accessible
    STATUS      current
    DESCRIPTION
        "Entries in this table represent switch interfaces and their matching
         VLAN translation Groups (identified through their Group IDs)"
    INDEX       { gamVlanTranslationConfigInterfacesIfIfIndex }
    ::= { gamVlanTranslationConfigInterfacesIfTable 1 }

GAMVlanTranslationConfigInterfacesIfEntry ::= SEQUENCE {
    gamVlanTranslationConfigInterfacesIfIfIndex  GAMInterfaceIndex,
    gamVlanTranslationConfigInterfacesIfGroupId  Integer32
}

gamVlanTranslationConfigInterfacesIfIfIndex OBJECT-TYPE
    SYNTAX      GAMInterfaceIndex
    MAX-ACCESS  accessible-for-notify
    STATUS      current
    DESCRIPTION
        "Interface index number."
    ::= { gamVlanTranslationConfigInterfacesIfEntry 1 }

gamVlanTranslationConfigInterfacesIfGroupId OBJECT-TYPE
    SYNTAX      Integer32 (1..65535)
    MAX-ACCESS  read-write
    STATUS      current
    DESCRIPTION
        "Group ID of the interface configuration."
    ::= { gamVlanTranslationConfigInterfacesIfEntry 2 }

gamVlanTranslationMibConformance OBJECT IDENTIFIER
    ::= { gamVlanTranslationMib 2 }

gamVlanTranslationMibCompliances OBJECT IDENTIFIER
    ::= { gamVlanTranslationMibConformance 1 }

gamVlanTranslationMibGroups OBJECT IDENTIFIER
    ::= { gamVlanTranslationMibConformance 2 }

gamVlanTranslationCapabilitiesInfoGroup OBJECT-GROUP
    OBJECTS     {                   gamVlanTranslationCapabilitiesMaxNumberOfTranslations }
    STATUS      current
    DESCRIPTION
        "A collection of objects."
    ::= { gamVlanTranslationMibGroups 1 }

gamVlanTranslationConfigTranslationTableInfoGroup OBJECT-GROUP
    OBJECTS     { gamVlanTranslationConfigTranslationGroupId,
                  gamVlanTranslationConfigTranslationVlanId,
                  gamVlanTranslationConfigTranslationTVlanId,
                  gamVlanTranslationConfigTranslationAction }
    STATUS      current
    DESCRIPTION
        "A collection of objects."
    ::= { gamVlanTranslationMibGroups 2 }

gamVlanTranslationConfigTranslationRowEditorInfoGroup OBJECT-GROUP
    OBJECTS     {                   gamVlanTranslationConfigTranslationRowEditorGroupId,
                  gamVlanTranslationConfigTranslationRowEditorVlanId,
                  gamVlanTranslationConfigTranslationRowEditorTVlanId,
                  gamVlanTranslationConfigTranslationRowEditorAction }
    STATUS      current
    DESCRIPTION
        "A collection of objects."
    ::= { gamVlanTranslationMibGroups 3 }

gamVlanTranslationConfigInterfacesIfTableInfoGroup OBJECT-GROUP
    OBJECTS     { gamVlanTranslationConfigInterfacesIfIfIndex,
                  gamVlanTranslationConfigInterfacesIfGroupId }
    STATUS      current
    DESCRIPTION
        "A collection of objects."
    ::= { gamVlanTranslationMibGroups 4 }

gamVlanTranslationMibCompliance MODULE-COMPLIANCE
    STATUS      current
    DESCRIPTION
        "The compliance statement for the implementation."

    MODULE      -- this module

    MANDATORY-GROUPS { gamVlanTranslationCapabilitiesInfoGroup,
                       gamVlanTranslationConfigTranslationTableInfoGroup,
                       gamVlanTranslationConfigTranslationRowEditorInfoGroup,
                       gamVlanTranslationConfigInterfacesIfTableInfoGroup }

    ::= { gamVlanTranslationMibCompliances 1 }

END
